/*
 * 
 * (c) Copyright RIFT.io, 2013-2016, All Rights Reserved
 *
 *
 */

module rw-config-agent-annotation
{
  namespace "http://riftio.com/ns/riftware-1.0/rw-config-agent-annotation";
  prefix "rw-config-agent-ann";

  import rw-config-agent {
    prefix rw-config-agent;
  }

  import tailf-common {
    prefix tailf;
  }

  tailf:annotate "/rw-config-agent:config-agent/rw-config-agent:account/rw-config-agent:connection-status" {
    tailf:callpoint rw_callpoint;
  }

  tailf:annotate "/rw-config-agent:update-cfg-agent-status" {
    tailf:actionpoint rw_actionpoint;
  }
}
