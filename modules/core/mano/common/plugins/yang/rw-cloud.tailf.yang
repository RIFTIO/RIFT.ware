/*
 * 
 * (c) Copyright RIFT.io, 2013-2016, All Rights Reserved
 *
 *
 */

module rw-cloud-annotation
{
  namespace "http://riftio.com/ns/riftware-1.0/rw-cloud-annotation";
  prefix "rw-cloud-ann";

  import rw-cloud {
    prefix rw-cloud;
  }

  import tailf-common {
    prefix tailf;
  }

  tailf:annotate "/rw-cloud:cloud/rw-cloud:account/rw-cloud:connection-status" {
    tailf:callpoint rw_callpoint;
  }

  tailf:annotate "/rw-cloud:update-cloud-status" {
    tailf:actionpoint rw_actionpoint;
  }
}
