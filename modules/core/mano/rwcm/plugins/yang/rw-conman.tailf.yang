module rw-conman-annotation
{
  namespace "http://riftio.com/ns/riftware-1.0/rw-conman-annotation";
  prefix "rw-conman-ann";

  import tailf-common {
    prefix tailf;
  }

  import rw-conman {
    prefix conman;
  }

  tailf:annotate "/conman:cm-state" {
    tailf:callpoint rw_callpoint;
  }
  
}
