/*
 * 
 * (c) Copyright RIFT.io, 2013-2016, All Rights Reserved
 *
 */



/**
 * @file rw-monitor.yang
 * @author Joshua Downer
 * @date 2015/10/30
 * @brief NFVI Monitor
 */

module rw-monitor
{
  namespace "http://riftio.com/ns/riftware-1.0/rw-monitor";
  prefix "rw-monitor";

  import rw-pb-ext {
    prefix "rwpb";
  }

  import rw-cli-ext {
    prefix "rwcli";
  }

  import rw-yang-types {
    prefix "rwt";
  }

  import rw-cloud {
    prefix "rw-cloud";
  }

  import rw-nsr {
    prefix "rw-nsr";
  }

  import rw-vnfr {
    prefix "rw-vnfr";
  }

  import rwcal {
    prefix "rwcal";
  }

  import ietf-yang-types {
    prefix "yang";
  }

  revision 2015-10-30 {
    description
      "Initial revision.";
  }
}
