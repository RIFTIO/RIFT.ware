/*
 * 
 * (c) Copyright RIFT.io, 2013-2016, All Rights Reserved
 *
 *
 */

module pnfd
{
  namespace "urn:ietf:params:xml:ns:yang:nfvo:pnfd";
  prefix "pnfd";

  import rw-pb-ext {
    prefix "rwpb";
  }

  import ietf-inet-types {
    prefix "inet";
  }

  import ietf-yang-types {
    prefix "yang";
  }

  import mano-types {
    prefix "manotypes";
  }

  revision 2015-09-10 {
    description
      "Initial revision. This YANG file defines 
       the Physical Network Function Descriptor (PNFD)";
    reference
      "Derived from earlier versions of base YANG files";
  }

  container pnfd-catalog {

    list pnfd {
      key "id";

      leaf id {
        description "Identifier for the PNFD.";
        type yang:uuid;
      }

      leaf name {
        description "PNFD name.";
        type string;
      }

      leaf short-name {
        description "PNFD short name.";
        type string;
      }

      leaf vendor {
        description "Vendor of the PNFD.";
        type string;
      }

      leaf description {
        description "Description of the PNFD.";
        type string;
      }

      leaf version {
        description "Version of the PNFD";
        type string;
      }

      list connection-point {
        description
            "List for external connection points. Each PNF has one or more external
            connection points.";
        key "id";
        leaf id {
          description
              "Identifier for the external connection points";
          type uint64;
        }

        leaf cp-type {
          description
              "Type of the connection point.";
          type manotypes:connection-point-type;
        }
      }
    }
  }
}
