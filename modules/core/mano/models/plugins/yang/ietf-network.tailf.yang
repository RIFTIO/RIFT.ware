/*
 * NO RW COPYRIGHT
 *
 */

module ietf-network-annotation
{
  namespace "urn:ietf:params:xml:ns:yang:ietf-network";
  prefix "ietf-network-ann";

  import tailf-common {
    prefix tailf;
  }

  import ietf-network {
    prefix nd;
  }

  tailf:annotate "/nd:network" {
      tailf:callpoint rw_callpoint;
  }

  tailf:annotate "/nd:network/nd:server-provided" {
      tailf:callpoint rw_callpoint;
  }
}
