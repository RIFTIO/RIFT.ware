/*
 * 
 * (c) Copyright RIFT.io, 2013-2016, All Rights Reserved
 *
 *
 */

module nsr-annotation
{
  namespace "http://riftio.com/ns/riftware-1.0/nsr-annotation";
  prefix "nsr-ann";

  import tailf-common {
    prefix tailf;
  }

  import nsr {
    prefix nsr;
  }

  tailf:annotate "/nsr:ns-instance-opdata" {
    tailf:callpoint rw_callpoint;
  }
  tailf:annotate "/nsr:exec-ns-config-primitive" {
     tailf:actionpoint rw_actionpoint;
  }
  tailf:annotate "/nsr:get-ns-config-primitive-values" {
     tailf:actionpoint rw_actionpoint;
  }
}
