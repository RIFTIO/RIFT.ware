/*
 * 
 * (c) Copyright RIFT.io, 2013-2016, All Rights Reserved
 *
 *
 */

module rw-nsr-annotation
{
  namespace "http://riftio.com/ns/riftware-1.0/rw-nsr-annotation";
  prefix "rw-nsr-ann";

  import tailf-common {
    prefix tailf;
  }

  import rw-nsr {
    prefix rw-nsr;
  }

  import nsr {
    prefix nsr;
  }

  tailf:annotate "/nsr:ns-instance-opdata/nsr:nsr/rw-nsr:operational-events" {
    tailf:callpoint rw_callpoint;
  }

  tailf:annotate "/nsr:ns-instance-opdata/rw-nsr:nsd-ref-count" {
    tailf:callpoint rw_callpoint;
  }
}
