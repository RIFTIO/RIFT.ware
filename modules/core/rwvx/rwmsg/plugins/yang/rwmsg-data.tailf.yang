/*
 * STANDARD_RIFT_IO_COPYRIGHT
 *
 */

module rwmsg-data-tailf
{
  namespace "http://riftio.com/ns/riftware-1.0/rwmsg-data-tailf";
  prefix "rwmsg-data-tailf";

  import rwmsg-data {
    prefix "rwmsg";
  } 

  import tailf-common {
    prefix tailf;
  }

  tailf:annotate "/rwmsg:messaging" {
    tailf:callpoint rw_callpoint;
  }
}
