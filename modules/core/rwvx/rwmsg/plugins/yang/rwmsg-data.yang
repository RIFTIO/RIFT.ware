/* STANDARD_RIFT_IO_COPYRIGHT */
/**
 * @file rwmsg-data.yang
 * @author Grant Taylor
 * @date 2014/8/1
 * @brief RiftWare Yang data schema for the RW.Msg
 */

module rwmsg-data
{
  namespace "http://riftio.com/ns/riftware-1.0/rwmsg-data";
  prefix "rwmsg";

  import rw-base {
    prefix rwbase;
  }

  // new mode et al
  import rw-cli-ext { 
    prefix "rwcli";
  }

  import rw-pb-ext {
    prefix "rwpb";
  }

  import rw-yang-types {
    prefix "rwt";
  }

  description "RW.Msg data definitions";

  revision 2014-08-01 {
    description "Initial revision";
    reference "None";
  }

  typedef rwmsg_payload_yenum {
    type enumeration {
      enum RAW;  
      enum PBAPI;
      enum TEXT;
      enum MSGCTL;
    }
  }

  typedef rwmsg_methb_yenum {
    type enumeration { 
      enum SRVCHAN;
      enum BROSRVCHAN;
    }
  }

  typedef rwmsg_channel_yenum {
    type enumeration { 
      enum NULL;
      enum CLI;
      enum SRV;
      enum BROCLI;
      enum BROSRV;
      enum PEERCLI;
      enum PEERSRV;
    }
  }

  typedef rwmsg_skstate_yenum {
    type enumeration { 
      enum NNSK_IDLE;
      enum NNSK_CONNECTED;
    }
  }

  grouping sockets {
    list sockets {
      rwpb:msg-new Chansocket;
      description "Detail around a channel socket";
      key "pri";
      leaf pri {
        type uint8;
      }
      leaf paused {
        type boolean;
      }
      leaf connected {
        type boolean;
      }
      leaf state {
        type rwmsg_skstate_yenum;
      }
    }
  }

  grouping methbindings {
    list methbindings {
      rwpb:msg-new Methbinding;
      description "Detail around a method to channel binding";
      key "pathhash pbapi_srvno pbapi_methno";
      leaf btype {
	type rwmsg_methb_yenum;
      }
      leaf path {
	rwpb:field-inline true;
	rwpb:field-string-max 512;
	type string;
      }
      leaf pathhash {
	type uint64;
      }
      leaf payfmt {
	type rwmsg_payload_yenum;
      }
      leaf pbapi_srvno {
	type uint32;
      }
      leaf pbapi_methno {
	type uint32;
      }
      leaf methno {
	type uint32;
      }
      leaf srvchanct {
	description "Total number of srvchan(s) bound to this path/payfmt/methno";
	type uint32;
      }
    }
  }

  grouping channel_info {
    list channels {
      rwpb:msg-new Channelinfo;
      key "id";
      leaf type {
	description "Channel Type";
	type rwmsg_channel_yenum;
      }
      leaf clict {
        description "Number of clients";  // should be number of active or recent clients
        type uint32;	
      }
      leaf id {
	description "Channel ID";
	type uint64;
      }

      leaf peer_id {
	description "Peer ID";
	type uint64;
      }
      leaf peer_pid {
	description "Peer PID";
	type uint64;
      }
      leaf peer_ip {
	description "Peer IP";
	type rwt:ip-address;
	rwpb:field-string-max 46;
	rwpb:field-inline true;
      }

      // [bro]srvchan method table
      uses methbindings;

      // channel socket detail
      uses sockets;

      // brosrvchan clistream table for the channel?

      // reqs in channel's various queues / hashes...

      // stats...
    }
  }

  grouping channel_debug_info {
    list channels {
      rwpb:msg-new ChannelDebugInfo;
      key "chan_id";
      leaf chan_type {
        description "Channel Type";
        type rwmsg_channel_yenum;
      }
      leaf chan_id {
        description "Channel ID";
        type uint64;
      }
      // brosrvchan clistream table for the channel?

      // reqs in channel's various queues / hashes...

      // stats...
      choice stat {
        case clichan {
          container clichan-stats {
            //rwpb:msg-new ChannelDebugInfo_ClichanStats;
            list bnc {
              key "bnc-type";
              leaf bnc-type { description "bnc-type"; type string; }
              leaf count { description "count"; type uint64; }
            }
            leaf recv { description "recv"; type uint64; }
            leaf cancel { description "cancel"; type uint64; }
            leaf ss_pollout { description "ss_pollout"; type uint64; }
            leaf defer { description "defer"; type uint64; }
            leaf to_cansent { description "to_cansent"; type uint64; }
            leaf to_canreleased { description "to_canreleased"; type uint64; }
            leaf ack_sent { description "ack_sent"; type uint64; }
            leaf ack_piggy_sent { description "ack_piggy_sent"; type uint64; }
            leaf ack_miss { description "ack_miss"; type uint64; }
            leaf recv_noent { description "recv_noent"; type uint64; }
            leaf recv_dup { description "recv_dup"; type uint64; }
          }
        }
        case srvchan {
          container srvchan-stats {
            //rwpb:msg-new ChannelDebugInfo_SrvchanStats;
            list bnc {
              key "bnc-type";
              leaf bnc-type { description "bnc-type"; type string; }
              leaf count { description "count"; type uint64; }
            }
            leaf cancel { description "cancel"; type uint64; }
            leaf cancel_unk { description "cancel_unk"; type uint64; }
            leaf pending_donada { description "pending_donada"; type uint64; }
            leaf cached_resend { description "cached_resend"; type uint64; }
            leaf seqzero_recvd { description "seqzero_recvd"; type uint64; }
          }
        }
      }
    }
  }


  grouping rwbroker_info {
    list broker {
      rwpb:msg-new Brokerinfo;
      description "Broker Status";
      key "tasklet-name";

      leaf tasklet-name {
	description "Tasklet name of this broker";
	type string;
      }

      leaf instance_uri {
	description "URI for this broker";
	type string;
      }

      uses channel_info;
    }
  }

  // show messaging ( info | ... )
  container messaging {
    config false;

    container info {
      rwpb:msg-new Rwmsg;
      rwpb:field-inline true;

      uses rwbroker_info;
    }

    container audit {
      list broker {
        key "tasklet-name";

        leaf tasklet-name {
          description "Tasklet name of this broker";
          type string;
        }
        leaf started {
          type boolean;
        }
        leaf completed {
          type boolean;
        }
        leaf succeeded {
          type boolean;
        }
        leaf completed_secs_back {
          type uint64;
        }
      }
    }

    container debug-info {
      list broker {
        key "tasklet-name";

        leaf tasklet-name {
          description "Tasklet name of this broker";
          type string;
        }
        uses channel_debug_info;
      }
    }
  }


} // module rwmsg-data
