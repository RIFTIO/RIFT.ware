/*
 * STANDARD_RIFT_IO_COPYRIGHT
 *
 */

module rw-logtest
{
  namespace "http://riftio.com/ns/riftware-1.0/rw-logtest";
  prefix "rwlogtest";

  import rw-pb-ext {
    prefix "rwpb";
  }

  import rw-notify-ext {
    prefix "rwnotify";
  }

  import rw-log {
    prefix "rwlog";
  }

  revision 2014-05-29 {
    description
      "Initial revision. This YANG file defines common groupings, typedefs, and
       containers available on Riftware for logging";
    reference
      "Derived from earlier versions of base YANG files";
  }

  notification fastpath-event-log-test1-emergency {
    rwnotify:log-event-id 00001011;
      description
         "Testing123";
      uses rwlog:severity-emergency;
  }

  notification fastpath-event-log-test-emergency {
    rwnotify:log-event-id 00001000;
      description
         "Testing123";
      uses rwlog:severity-emergency;
      leaf data { type string; }
  }
  notification fastpath-event-log-test-alert {
    rwnotify:log-event-id 00001001;
      description
         "Testing123";
      uses rwlog:severity-alert;
      leaf data { type string; }
  }
  notification fastpath-event-log-test-critical {
    rwnotify:log-event-id 00001002;
      description
         "Testing123";
      uses rwlog:severity-critical;
      leaf data { type string; }
  }
  notification fastpath-event-log-test-warning {
    rwnotify:log-event-id 00001003;
      description
         "Testing123";
      uses rwlog:severity-warning;
      leaf data { type string; }
  }
  notification fastpath-event-log-test-error {
    rwnotify:log-event-id 00001004;
      description
         "Testing123";
      uses rwlog:severity-error;
      leaf data { type string; }
  }
  notification fastpath-event-log-test-info {
    rwnotify:log-event-id 00001005;
      description
         "Testing123";
      uses rwlog:severity-info;
      leaf data { type string; }
  }
  notification fastpath-event-log-test-debug {
    rwnotify:log-event-id 00001006;
      description
         "Testing123";
      uses rwlog:severity-debug;
      leaf data { type string; }
  }
  notification fastpath-event-log-test{
    rwnotify:log-event-id 00001007;
      description
         "Testing123";
      uses rwlog:severity-error;
      leaf data { type string; }
  }
  notification fastpath_ev_port_state_change {
    rwnotify:log-event-id 00001008;
    description
      "CLI command audit history";
    uses rwlog:severity-critical;
    leaf portnumber {
      type string;
      description "Port Name";
      rwpb:field-inline "true";
      rwpb:field-string-max "128";
    }
    leaf operstate {
      type string;
      description "Operational status";
      rwpb:field-string-max "16";
    }
    leaf serialnumber {
      type string;
      description "Serial Number";
      rwpb:field-string-max "32";
    }
  }
  notification fastpath_packet_trace {
    rwnotify:log-event-id 00001009;
    description "Packet trace";
    uses rwlog:severity-debug;

    uses rwlog:packet-info;
  }

  notification callid-test {
    rwnotify:log-event-id 999;
    description "Testing123";
    uses rwlog:severity-debug;
    leaf data { type string; }
  }

  notification callid-imsi-test {
    rwnotify:log-event-id 00001006;
    description "IMSI filter attribute and callid test";
    uses rwlog:severity-debug;
    leaf imsi {type string; }
    leaf data { type string; }
  }

  notification callid-test2 {
    rwnotify:log-event-id 00001007;
    description "New callid test";
    uses rwlog:severity-debug;
    leaf data { type string; }
  }

  notification callid-invalidate-test {
    rwnotify:log-event-id 00001008;
    description "New callid invalidate test";
    uses rwlog:severity-debug;
    uses rwlog:invalidate-call-params;
    leaf msg {type string; }
  }

  notification call-failure-test {
    rwnotify:log-event-id 00001009;
    description "Call failure test";
    uses rwlog:severity-error;
    uses rwlog:call-failure-params;
  }

  notification call-failure-debug-test {
    rwnotify:log-event-id 00001010;
    description "Call failure debug test";
    uses rwlog:severity-debug;
    uses rwlog:call-failure-params;
  }

  notification log-info-critinfo {
    rwnotify:log-event-id 00001011;
      description
         "Testing123";
      uses rwlog:severity-info-critinfo;
      leaf data { type string; }
  }
  notification log-debug-critinfo {
    rwnotify:log-event-id 00001012;
      description
         "Testing123";
      uses rwlog:severity-debug-critinfo;
      leaf data { type string; }
  }
  notification log-error-critinfo {
    rwnotify:log-event-id 00001013;
      description
         "Testing123";
      uses rwlog:severity-error-critinfo;
      leaf data { type string; }
  }

  notification log-with-vnf {
    rwnotify:log-event-id 00001014;
      description
         "Testing123";
      uses rwlog:severity-error;

      uses rwlog:vnf-identifiation;
      leaf data { type string; }
  }
}
