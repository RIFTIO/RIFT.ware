/* STANDARD_RIFT_IO_COPYRIGHT */

/**
 * @file rwshell-mgmt.yang
 * @date 2015/05/20
 * @brief RiftWare CLI for System Management
 */

module rwshell-mgmt
{
  namespace "http://riftio.com/ns/riftware-1.0/rwshell-mgmt";
  prefix "rwshell-mgmt";

  import rw-pb-ext {
    prefix "rwpb";
  }
  import rw-log {
    prefix "rwlog";
  }
  import rw-yang-types {
    prefix "rwt";
  }
  import rw-cli-ext {
    prefix "rwcli";
  }
  revision 2015-05-20 {
    description "Initial revision.";
    reference "RIFT Event Logging Subsystem";
  }


  rpc profiler-start {                                                                                                                                                                                                                                                      
    input {
      leaf vm-name {
        description "Name of VM (or 'all')";
        type string;
      }
      leaf frequency {
        description "Number of samples per second";
        type uint32;
      }
    }
    output {
      list vm {
        key name;
        
        leaf name {
          description "Name of the VM";
          type string;
        }
        leaf-list command {
          description "command executed";
          type string;
        }
      }
    }
  }

  rpc profiler-stop {
    input {
      leaf vm-name {
        description "Name of the VM";
        type string;
      }
    }
    output {
      list vm {
        key name;
        
        leaf name {
          description "Name of the VM";
          type string;
        }
        leaf-list command {
          description "command executed";
          type string;
        }
      }
    }
  }

  rpc profiler-report {
    input {
      leaf vm-name {
        description "Name of the VM";
        type string;
      }
      leaf percent-limit {
        description "Do not show entries which have an overhead under that percent. (Default: 1%)";
        type decimal64 {
          fraction-digits 5;
          range 0..100;
        }
      }
    }
    output {
      list vm {
        key name;

        leaf name {
          description "Name of the VM";
          type string;
        }
        leaf-list command {
          description "command executed";
          type string;
        }
        leaf-list out-data {
          type string;
        }
      }
    }
  }

  container crash {
    config false;
    description "Crash related information";

    container list {
      list vm {
        key name;

        leaf name {
          type string;
        }

        list backtrace {
          key id;

          leaf id {
            type uint32;
          }
          leaf detail {
            type string;
          }
        }
      }
    }
  }

  container profiler {
    config false;
    description "Profiler-report from background profiler";

    container report {
      list vm {
        key name;
        
        leaf name {
          description "Name of the VM";
          type string;
        }
        leaf command {
          description "command executed";
          type string;
        }
        leaf out-data {
          description "output data";
          type string;
        }
      }
    }
  }

  container background-profiler {
    description "Configuring background profiler";

    container enable {
      leaf vm-name {
        description "Name of the VM";
        type string;
      }
      leaf frequency {
        description "Number of samples per second";
        type uint32;
      }
    }

    container disable {
      leaf vm-name {
        description "Name of the VM";
        type string;
      }
    }

  }

}
