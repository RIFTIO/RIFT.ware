/* STANDARD_RIFT_IO_COPYRIGHT */

/**
 * @file dts-test.yang
 * @author Rajesh Velandy
 * @date 2014/08/08
 * @brief Top-level yang for testing libncx.
 */

module testdts-rw-stats
{
  namespace "http://riftio.com/ns/core/rwvx/rwdts/test/yang/testdts-rw-stats";
  prefix "tdtsstats";

  import rw-pb-ext { prefix "rwpb"; }

  description
    "This yang models stats";

  revision 2015-07-13 {
    description "Initial version"; }

  grouping routerstats {
    container stats {
      rwpb:msg-new Routerstats;
      description "DTS router statistics";

      leaf topx-begin {
        type uint64;
      }

      leaf topx-begin-tran {
        type uint64;
      }
      leaf topx-begin-notran {
        type uint64;
      }
      leaf topx-end {
        type uint64;
      }
      leaf topx-end-notran-success {
        type uint64;
      }
      leaf topx-end-notran-fail {
        type uint64;
      }
      leaf topx-end-commit {
        type uint64;
      }
      leaf topx-end-abort {
        type uint64;
      }
      leaf topx-end-fail {
        type uint64;
      }
      leaf topx-count-5s {
        type uint64;
      }
      leaf topx-rate-5s {
        type uint64;
      }
      leaf topx-latency-5s {
        type uint64;
      }
    }
  }

  container dts {
    uses routerstats;
  }
}
