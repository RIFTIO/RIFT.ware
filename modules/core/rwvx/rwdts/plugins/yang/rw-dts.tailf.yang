/*
 * STANDARD_RIFT_IO_COPYRIGHT
 *
 */

module rw-dts-tailf
{
  namespace "http://riftio.com/ns/riftware-1.0/rw-dts-tailf";
  prefix "rw-dts-tailf";

  import rw-dts {
    prefix rwdts;
  }

  import tailf-common {
    prefix tailf;
  }

  tailf:annotate "/rwdts:dts/rwdts:member" {
    tailf:callpoint rw_callpoint;
  }

  tailf:annotate "/rwdts:dts/rwdts:routers" {
    tailf:callpoint rw_callpoint;
  }
  
  tailf:annotate "/rwdts:rtr-init-reg-id" {
    tailf:callpoint rw_callpoint;
  }

  tailf:annotate "/rwdts:rtr-init-reg-keyspec" {
    tailf:callpoint rw_callpoint;
  }

  tailf:annotate "/rwdts:rtr-peer-reg-keyspec" {
    tailf:callpoint rw_callpoint;
  }

  tailf:annotate "/rwdts:member-info-bcast" {
    tailf:callpoint rw_callpoint;
  }
  
  tailf:annotate "/rwdts:journal-info" {
    tailf:callpoint rw_callpoint;
  }

  tailf:annotate "/rwdts:start-dts" {
    tailf:actionpoint rw_actionpoint;
  }

  tailf:annotate "/rwdts:stop-dts" {
    tailf:actionpoint rw_actionpoint;
  }

}
