/*
 * STANDARD_RIFT_IO_COPYRIGHT
 *
 */

module rw-dtsperfmgr-annotation
{
  namespace "http://riftio.com/ns/riftware-1.0/rw-dtsperfmgr-annotation";
  prefix "rw-dtsperfmgr-ann";

  import tailf-common {
    prefix tailf;
  }

  import rw-dtsperfmgr {
    prefix rw-dtsperfmgr;
  }

  tailf:annotate "/rw-dtsperfmgr:start-perf-test" {
    tailf:actionpoint rw_actionpoint;
  }
  tailf:annotate "/rw-dtsperfmgr:stop-perf-test" {
    tailf:actionpoint rw_actionpoint;
  }
  tailf:annotate "/rw-dtsperfmgr:perf-test" {
    tailf:callpoint rw_callpoint;
  }
}
