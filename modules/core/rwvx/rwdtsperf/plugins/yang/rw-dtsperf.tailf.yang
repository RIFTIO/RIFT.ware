/*
 * STANDARD_RIFT_IO_COPYRIGHT
 *
 */

module rw-dtsperf-annotation
{
  namespace "http://riftio.com/ns/riftware-1.0/rw-dtsperf-annotation";
  prefix "rw-dtsperf-ann";

  import tailf-common {
    prefix tailf;
  }

  import rw-dtsperf {
    prefix rwdtsperf;
  }

  tailf:annotate "/rwdtsperf:perf-statistics" {
    tailf:callpoint rw_callpoint;
  }
  tailf:annotate "/rwdtsperf:start-xact" {
    tailf:actionpoint rw_actionpoint;
  }
}
