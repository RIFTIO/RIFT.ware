/*
 * STANDARD_RIFT_IO_COPYRIGHT
 *
 */

module rw-base-annotation
{
  namespace "http://riftio.com/ns/riftware-1.0/rw-base-annotation";
  prefix "rw-base-ann";

  import rw-base {
    prefix rwbase;
  }

  import tailf-common {
    prefix tailf;
  }


  tailf:annotate "/rwbase:vcs/rwbase:info" {
    tailf:callpoint rw_callpoint;
  }

  tailf:annotate "/rwbase:vcs/rwbase:instances" {
    tailf:callpoint rw_callpoint;
  }

  tailf:annotate "/rwbase:version" {
    tailf:callpoint rw_callpoint;
  }

  tailf:annotate "/rwbase:uptime" {
    tailf:callpoint rw_callpoint;
  }

  tailf:annotate "/rwbase:vcs/rwbase:resource/rwbase:utilization" {
    tailf:callpoint rw_callpoint;
  }

  tailf:annotate "/rwbase:tracing" {
    tailf:actionpoint rw_actionpoint;
  }

  tailf:annotate "/rwbase:tracing" {
    tailf:actionpoint rw_actionpoint;
  }

}
