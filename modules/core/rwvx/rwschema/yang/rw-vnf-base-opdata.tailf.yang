/*
 * STANDARD_RIFT_IO_COPYRIGHT
 *
 */

module rw-vnf-base-opdata.tailf
{
  namespace "http://riftio.com/ns/riftware-1.0/rw-vnf-base-opdata-annotation";
  prefix "rw-vnf-base-opdata-ann";
    
  import mano-base {
    prefix manobase;
  }
  import rw-vnf-base-opdata {
    prefix rwvnfbaseopdata;
  }
  import tailf-common {
    prefix tailf;
  }

  tailf:annotate "/manobase:vnf-opdata/manobase:vnf/rwvnfbaseopdata:logical-port" {
    tailf:callpoint rw_callpoint;
  }
  tailf:annotate "/manobase:vnf-opdata/manobase:vnf/rwvnfbaseopdata:port-state" {
    tailf:callpoint rw_callpoint;
  }
  tailf:annotate "/manobase:vnf-opdata/manobase:vnf/rwvnfbaseopdata:network-context-state" {
    tailf:callpoint rw_callpoint;
  }
  tailf:annotate "/rwvnfbaseopdata:clear-data" {
    tailf:actionpoint rw_actionpoint;
  }
  tailf:annotate "/rwvnfbaseopdata:start" {
    tailf:actionpoint rw_actionpoint;
  }
  tailf:annotate "/rwvnfbaseopdata:insmod" {
    tailf:actionpoint rw_actionpoint;
  }
  tailf:annotate "/rwvnfbaseopdata:stop" {
    tailf:actionpoint rw_actionpoint;
  }
  tailf:annotate "/manobase:vnf-opdata/manobase:vnf/rwvnfbaseopdata:virtual-fabric-access-point" {
    tailf:callpoint rw_callpoint;
  }
  tailf:annotate "/manobase:vnf-opdata/manobase:vnf/rwvnfbaseopdata:virtual-service-access-point" {
    tailf:callpoint rw_callpoint;
  }
  tailf:annotate "/manobase:vnf-opdata/manobase:vnf/rwvnfbaseopdata:flow-hashbin" {
    tailf:callpoint rw_callpoint;
  }
  tailf:annotate "/manobase:vnf-opdata/manobase:vnf/rwvnfbaseopdata:flow-signature" {
    tailf:callpoint rw_callpoint;
  }
  tailf:annotate "/manobase:vnf-opdata/manobase:vnf/rwvnfbaseopdata:classifiers" {
    tailf:callpoint rw_callpoint;
  }
}
