/*
 * STANDARD_RIFT_IO_COPYRIGHT
 *
 */

module rw-mgmt-schema.tailf {

  namespace "http://riftio.com/ns/riftware-1.0/rw-mgmt-schema-annotation";
  prefix "rw-mgmt-schema-ann";

  import rw-mgmt-schema
  {
    prefix rw-mgmt-schema;
  }

  import tailf-common {
    prefix tailf;
  }

  tailf:annotate "/rw-mgmt-schema:rw-mgmt-schema/rw-mgmt-schema:schema-version" {
    tailf:cdb-oper {
      tailf:persistent true;
    }
  } 

}
