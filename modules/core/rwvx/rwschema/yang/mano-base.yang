/*
 * STANDARD_RIFT_IO_COPYRIGHT
 *
 */

module mano-base
{
  namespace "http://riftio.com/ns/riftware-1.0/mano-base";
  prefix "manobase";

  import ietf-yang-types {
    prefix "yang";
  }

  import rw-cli-ext {
    prefix "rwcli";
  }

  revision 2015-08-25 {
    description
      "This YANG file provides agument points for VNF specific 
       configuration and operational data";
    reference
      "Derived from earlier versions of base YANG files";
  }

  container vnf-config {
    description
        "Container for VNF configuration data";
    list vnf {
      description
          "The VNF configuration data YANG moodel augments this path";
      rwcli:new-mode "vnf";
      key "name instance";
      leaf name {
        description
            "Name of the VNF.";
        type string;
      }
      leaf instance{
        description
          "Instance number of the VNF.";
        type uint32;
      }
      leaf id {
        description
            "Identifier for the VNF";
        type yang:uuid;
      }
    }
  }

  container vnf-opdata {
    description
        "Container for VNF operational data";
    config false;
    list vnf {
      description
          "The VNF operational data YANG model augments this path";
      key "name instance";
      config false;
      leaf name {
        description
          "Name of the VNF.";
        type string;
      }
      leaf instance{
        description
          "Instance number of the VNF.";
        type uint32;
      }
      leaf id {
        description
            "Identifier for the VNF";
        type yang:uuid;
      }
    }
  }
}
