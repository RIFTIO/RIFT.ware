/*
 * STANDARD_RIFT_IO_COPYRIGHT
 *
 */

module toy-vnf-opdata
{
  namespace "http://riftio.com/ns/riftware-1.0/toy-vnf-opdata";
  prefix "toyvnfopdata";

  import mano-base {
    prefix manobase;
  }

  revision 2015-08-25 {
    description "Toy vnf configuration";
  }

  augment /manobase:vnf-opdata/manobase:vnf {
    container toy-opdata {
      description 
          "Container for toy VNF operational data.";
      leaf name {
        type string;
      }
    }
  }
}
