/*
 * STANDARD_RIFT_IO_COPYRIGHT
 *
 */

module rw-ha
{
  namespace "http://riftio.com/ns/riftware-1.0/rw-ha";
  prefix "rw-ha";

  import rw-pb-ext {
    prefix "rwpb";
  }

  import rwvcs-types {
    prefix "rwvcstypes";
  }

  revision 2016-06-16 {
    description "Initial revision";
    reference "RIFT High Availability";
  }

  container ha-uagent-state {
    description
      "Information pertaining to the ha-state of the Management Agent";
    rwpb:msg-new HAState;
    config false;

    container ha-config-state {
      leaf ready {
        description
          "Indicates readiness of critical tasks, schema loading and init configuration";
        type boolean;
        default false;
      }
    }
  }

  list mode-change-info {
    config false;
    key rwvm-instance-name;
    leaf rwvm-instance-name {
      type string;
    }
    list instances {
      key instance-name;
      leaf instance-name {
        type string;
      }
      leaf vm-state {
        type rwvcstypes:vm-state;
      }
    }
  }

  container active-mgmt-info {
    config false;
    leaf mgmt-vm-instance-name {
      type string;
    }
    leaf mgmt-ip-address {
      type string;
    }
  }
}
