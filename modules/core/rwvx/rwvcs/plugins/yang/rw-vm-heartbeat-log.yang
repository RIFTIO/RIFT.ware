/* STANDARD_RIFT_IO_COPYRIGHT */

/**
 * @file rw-vm-heartbeat-log.yang
 * @author Suresh Balakrishnan
 * @date 08/01/2015
 * @brief RiftWare CLI for Serf Logging
 */

module rw-vm-heartbeat-log
{
  namespace "http://riftio.com/ns/riftware-1.0/rwvm-heartbeat-log";
  prefix "rwvmhblog";

  import rw-base {
    prefix rwbase;
  }

  import rw-pb-ext {
    prefix "rwpb";
  }

  import rw-yang-types {
    prefix "rwt";
  }

  import rw-notify-ext {
    prefix "rwnotify";
  }

  import rw-log {
    prefix "rwlog";
  }

  revision 2014-08-11 {
    description
      "Initial revision.";
    reference
      "RIFT Application Manager Logging";
  }

  /* Serf Logs - ID Space 00050000- 00050999 */

  notification serf-monitor-debug {
    rwnotify:log-event-id 00050000;
      description
         "Serf Monitor Debug Log";
      uses rwlog:severity-debug;
      leaf log  {
        type string;
      }
  }

  notification serf-monitor-info {
    rwnotify:log-event-id 00050001;
      description
         "Serf Monitor Info Log";
      uses rwlog:severity-info;
      leaf log  {
        type string;
      }
  }

  notification serf-monitor-warn {
    rwnotify:log-event-id 00050002;
      description
         "Serf Monitor Warning Log";
      uses rwlog:severity-warning;
      leaf log  {
        type string;
      }
  }

  notification serf-monitor-error {
    rwnotify:log-event-id 00050003;
      description
         "Serf Monitor Error Log";
      uses rwlog:severity-error;
      leaf log  {
        type string;
      }
  }

  notification msgpack-decode-error {
    rwnotify:log-event-id 00050004;
      description
         "Serf Msgpack Decoding Error Log";
      uses rwlog:severity-warning;
      leaf log  {
        type string;
      }
  }

  notification member-unpack-error {
    rwnotify:log-event-id 00050005;
      description
         "Serf Memeber unpack Error Log";
      uses rwlog:severity-warning;
      leaf log  {
        type string;
      }
  }

  notification misc-error {
    rwnotify:log-event-id 00050006;
      description
         "Serf RPC client misc error Log";
      uses rwlog:severity-error;
      leaf log  {
        type string;
      }
      leaf error {
        type int32;
      }
  }

  notification trace-info {
    rwnotify:log-event-id 00050007;
      description
         "Serf RPC client trace info";
      uses rwlog:severity-info;
      leaf log  {
        type string;
      }
  }

  notification leadvm-unavailable {
    rwnotify:log-event-id 00050008;
      description
         "Serf Lead VM unavailable";
      uses rwlog:severity-error;
      leaf log  {
        type string;
      }
      leaf instance_name {
        type string;
      }
  }

  notification rpc-connect-failed {
    rwnotify:log-event-id 00050009;
      description
         "Serf RPC connect failed";
      uses rwlog:severity-error;
      leaf log  {
        type string;
      }
      leaf rpc_address {
        type string;
      }
  }

  notification serf-rpc-started {
    rwnotify:log-event-id 00050010;
      description
         "Serf RPC connection started";
      uses rwlog:severity-info;
      leaf log  {
        type string;
      }
      leaf rpc_address {
        type string;
      }
  }

  notification serf-event-processing-failed {
    rwnotify:log-event-id 00050011;
      description
         "Serf RPC event process failed";
      uses rwlog:severity-warning;
      leaf log  {
        type string;
      }
      leaf rpc_address {
        type string;
      }
  }

  notification serf-not-started {
    rwnotify:log-event-id 00050012;
      description
         "Serf not started info log";
      uses rwlog:severity-info;
      leaf log  {
        type string;
      }
      leaf instance_name {
        type string;
      }
      leaf vm_ip_address {
        type string;
      }
  }

  notification serf-starting {
    rwnotify:log-event-id 00050013;
      description
         "Serf starting info log";
      uses rwlog:severity-info;
      leaf instance_name {
        type string;
      }
      leaf vm_ip_address {
        type string;
      }
  }


  /*
   * END - Serf Log space : 00050000 - 00050100
   */
}
