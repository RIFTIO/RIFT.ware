/*
 * STANDARD_RIFT_IO_COPYRIGHT
 *
 */

module rw-dynschema-log {
  namespace "http://riftio.com/ns/riftware-1.0/rwvcs-dynschema-log";
  prefix "rwdynschemalog";

  import rw-base {
    prefix rwbase;
  }

  import rw-pb-ext {
    prefix "rwpb";
  }

  import rw-yang-types {
    prefix "rwt";
  }

  import rw-notify-ext {
    prefix "rw-notify";
  }

  import rw-log {
    prefix "rw-log";
  } 

  revision 2015-10-14 {
    description
      "Initial revision";
    reference
      "RIFT dynamic schema logging";
  }

  /* Dynamic Schema Logging 72000-72100 */
  notification info {
    rw-notify:log-event-id 00072001;
    description "Dynamic schema info notifications";
    uses rw-log:severity-info;

    leaf instance {
      type rw-log:pointer;
    }
    leaf log {
      type string;
    }
  }

  notification crit-info {
    rw-notify:log-event-id 00072002;
    description "Dynamic schema critical info notifications";
    uses rw-log:severity-info-critinfo;

    leaf instance {
      type rw-log:pointer;
    }
    leaf log {
      type string;
    }
  }

  notification notice {
    rw-notify:log-event-id 00072003;
    description "Dynamic schema notifications";
    uses rw-log:severity-notice;

    leaf instance {
      type rw-log:pointer;
    }

    leaf log {
      type string;
    }
  }

  notification error {
    rw-notify:log-event-id 00072004;
    description "Dynamic schema error notification";
    uses rw-log:severity-error;

    leaf instance {
      type rw-log:pointer;
    }

    leaf log {
      type string;
    }
  }

  notification debug {
    rw-notify:log-event-id 00072005;
    description "Dynamic schema debug notifications";
    uses rw-log:severity-debug;

    leaf instance {
      type rw-log:pointer;
    }

    leaf log {
      type string;
    }
  }

}
