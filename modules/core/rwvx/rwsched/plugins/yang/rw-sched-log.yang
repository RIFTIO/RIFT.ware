/* STANDARD-RIFT-IO-COPYRIGHT */
/**
 * @file   rwsched-log.yang
 * @author Prashanth Bhaskar
 * @date   2015/10/14
 * @brief  Riftware yang data schema for RwSched logging
 */

module rw-sched-log
{
  namespace "http://riftio.com/ns/riftware-1.0/rwschedlog";
  prefix "rwschedlog";


  import rw-base {
    prefix rwbase;
  }

  import rw-pb-ext {
    prefix "rwpb";
  }

  import rw-yang-types {
    prefix "rwt";
  }

  import rw-notify-ext {
    prefix "rwnotify";
  }

  import rw-log {
    prefix "rwlog";
  }

  description "RW.Sched logging definitions";

  revision 2015-10-14 {
    description "Initial revision";
    reference "Rift Yang Data schema for RwSched Logging";
  }

  notification sched-debug {
    rwnotify:log-event-id 00080000;
    description "RwScheduler generic debug log";
    uses rwlog:severity-debug;
    leaf log {
      type string;
    }
  }

  notification sched-info {
    rwnotify:log-event-id 00080001;
    description "RwScheduler generic info log";
    uses rwlog:severity-info;
    leaf log {
      type string;
    }
  }

  notification sched-notice {
    rwnotify:log-event-id 00080002;
    description "RwScheduler generic notice log";
    uses rwlog:severity-notice;
    leaf log {
      type string;
    }
  }

  notification sched-warning {
    rwnotify:log-event-id 00080003;
    description "RwScheduler generic warning log";
    uses rwlog:severity-warning;
    leaf log {
      type string;
    }
  }

  notification sched-error {
    rwnotify:log-event-id 00080004;
    description "RwScheduler generic error log";
    uses rwlog:severity-error;
    leaf log {
      type string;
    }
  }

  notification sched-critical {
    rwnotify:log-event-id 00080005;
    description "RwScheduler generic critical log";
    uses rwlog:severity-critical;
    leaf log {
      type string;
    }
  }

  notification sched-alert {
    rwnotify:log-event-id 00080006;
    description "RwScheduler generic alert log";
    uses rwlog:severity-alert;
    leaf log {
      type string;
    }
  }

  notification sched-emergency {
    rwnotify:log-event-id 00080007;
    description "DTS API generic emergency log";
    uses rwlog:severity-emergency;
    leaf log {
      type string;
    }
  }
} // module rw-sched-log
