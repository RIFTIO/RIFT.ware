/*
 * STANDARD_RIFT_IO_COPYRIGHT
 *
 */

module rw-memlog
{
  namespace "http://riftio.com/ns/riftware-1.0/rw-memlog";
  prefix "rw-memlog";

  import rw-pb-ext {
    prefix "rwpb";
  }

  description
    "Defines and configures RIFT.ware in-memory tracing and logging
    facility.";

  revision 2015-09-11 {
    description
      "Initial revision.";
  }

  container rw-memlog {
    description
      "Configuration for the RIFT.ware in-memory tracing facility.";
    config true;
    rwpb:msg-new MemlogConfig;

    list tasklet {
      key tasklet-name;
      leaf tasklet-name {
        description
          "Tasklet name.";
        type string;
      }

      list instance {
        key instance-name;
        rwpb:msg-new InstanceConfig;

        leaf instance-name {
          description
            "Memory logging instance name.  There may be more than one
            instance in each tasklet.";
          type string;
        }

        leaf minimum-retired-count {
          description
            "The minimum number of buffers to retain on the retired
            list.  Retired buffers form a historical record of what
            happened in the past.";
          type uint32 {
            range "2..max";
          }
        }

        leaf maximum-keep-count {
          description
            "The maximum number of kept buffers.  Kept buffers are
            retired buffers that have been specifically marked as more
            interesting than the others, so they will not be reused as
            quickly.";
          type uint32;
        }

        leaf filter-mask {
          description
            "The desired filter-mask setting.  Invalid flags will be
            ignored, rather than fail configuration.";
          // ATTN: Should be bits, but bits not yet supported.
          type uint64;
        }

      } // list instance
    } // list tasklet
  } // container rw-memlog-config


  container rw-memlog-state {
    description
      "State for the RIFT.ware in-memory tracing facility.";
    config false;
    rwpb:msg-new MemlogState;

    list tasklet {
      key tasklet-name;

      leaf tasklet-name {
        description
          "Tasklet name.";
        type string;
      }

      list instance {
        key instance-name;
        rwpb:msg-new InstanceState;

        leaf instance-name {
          description
            "Memory logging instance name.  There may be more than one
            instance in each tasklet.";
          type string;
        }

        leaf buffer-count {
          description
            "The number of buffers current allocated.";
          type uint64;
        }

        leaf filter-mask {
          description
            "The current filter flags.";
          // ATTN: Should be bits, but bits not yet supported.
          type uint64;
        }

        list buffer {
          // ATTN: perf hack: key address;

          leaf address {
            description
              "The address of the buffer.";
            type uint64;
          }

          leaf object-name {
            description
              "Description of the object that last used/is using this buffer.";
            type string;
          }

          leaf object-id {
            description
              "Object identifier for the object that last used/is using
              this buffer.";
            type uint64;
          }

          leaf version {
            description
              "Buffer version.  Each time the buffer is reused, the
              version number increases.";
            type uint32;
          }

          leaf time {
            description
              "If the buffer is active, the time the buffer was made
              active, in nanoseconds since the Unix epoch.  If the
              buffer is retired, the time the buffer was retired, in
              nanoseconds since the Unix epoch.";
            // ATTN: Should be decimal64, but not supported.
            type uint64;
            units "nanoseconds";
          }

          leaf is-active {
            description
              "True if the buffer is active.";
            type boolean;
          }

          leaf is-keep {
            description
              "True if the buffer is on the keep list.";
            type boolean;
          }

          list entry {
            // ATTN: perf hack: key index

            leaf index {
              description
                "The entry index.  Entries are numbered from 0.";
              type uint32;
            }

            leaf file {
              description
                "The name of the file that created the entry.";
              type string;
            }

            leaf line {
              description
                "The line number where the entry was created.";
              type uint32;
            }

            leaf arg0 {
              description "Log argument string.";
              type string;
            }

            leaf arg1 {
              description "Log argument string.";
              type string;
            }

            leaf arg2 {
              description "Log argument string.";
              type string;
            }

            leaf arg3 {
              description "Log argument string.";
              type string;
            }

            leaf arg4 {
              description "Log argument string.";
              type string;
            }

            leaf arg5 {
              description "Log argument string.";
              type string;
            }

            leaf arg6 {
              description "Log argument string.";
              type string;
            }

            leaf arg7 {
              description "Log argument string.";
              type string;
            }

            leaf arg8 {
              description "Log argument string.";
              type string;
            }

            leaf arg9 {
              description "Log argument string.";
              type string;
            }

          } // list entry
        } // list buffer
      } // list instance
    } // list tasklet
  } // container rw-memlog-state

  grouping buffer-id {

    leaf tasklet-name {
      description
        "Tasklet name.";
      type string;
    }

    leaf instance-name {
      description
        "Memory logging instance name.";
      type string;
    }

    leaf object-name {
      description
        "Description of the object that last used/is using this buffer.";
      type string;
    }

    leaf object-id {
      description
        "Object identifier for the object that last used/is using
        this buffer.";
      type uint64;
    }
  } // grouping buffer-id

  rpc rw-memlog-command {
    description
      "Commands for controlling RW.Memlog.";

    input {
      rwpb:msg-new Command;

      container clear {
        presence true;
        description
          "Clear all of the retired buffers in the matching instances.";

        uses buffer-id;

        leaf also-keep {
          description
            "Also clear all of the keep buffers.";
          type empty;
        }
      }

      container keep {
        presence true;
        description
          "Keep all of the retired buffers in the matching instances.";

        uses buffer-id;
      }
    }
  }


} // module rw-memlog
