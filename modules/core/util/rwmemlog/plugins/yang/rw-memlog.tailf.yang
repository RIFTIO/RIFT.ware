/*
 * STANDARD_RIFT_IO_COPYRIGHT
 *
 */

module rw-memlog.tailf
{
  namespace "http://riftio.com/ns/riftware-1.0/rw-memlog.tailf";
  prefix "rw-memlog-ann";

  import tailf-common {
    prefix tailf;
  }

  import rw-memlog {
    prefix rw-memlog;
  }

  tailf:annotate "/rw-memlog:rw-memlog-state" {
    tailf:callpoint rw_callpoint;
  }

  tailf:annotate "/rw-memlog:rw-memlog-command" {
    tailf:actionpoint rw_actionpoint;
  }
}
