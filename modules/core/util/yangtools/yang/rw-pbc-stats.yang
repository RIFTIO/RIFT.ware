/* STANDARD_RIFT_IO_COPYRIGHT */
/**
 * @file rw-pbc-stats.yang
 * @author Sujithra Periasamy
 * @date 2015/07/01
 * @brief protobuf-c stats
 * 
 * Yang module for protobuf-c API and error statistics.
 */

module rw-pbc-stats
{
  namespace "http://riftio.com/ns/riftware-1.0/rw-pbc-stats";
  prefix "rwpbc";

  import rw-pb-ext {
    prefix "rwpb";
  }

  import rw-yang-types {
    prefix "rwt";
  }

  description
   "Data model for protobuf-c API, error and related statistics";

  revision 2015-07-01 {
    description "Initial revision.";
  }

  container pbc-stats {
    config false;
    description "Container for protobufc api stats";

    list member {

      key "name";
      description "List of dts members";

      leaf name {
        type string;
        description "Name of the member";
        rwpb:field-inline "true";
        rwpb:field-string-max 256;
      }

      container fcall-stats {

        rwpb:field-inline "true";
        rwpb:msg-flat "true";
        description "Container for fcall-stats";

        leaf pack {
          type uint64;
        }

        leaf get-pack-sz {
          type uint64;
        }

        leaf pack-to-buffer {
          type uint64;
        }

        leaf unpack {
          type uint64;
        }

        leaf check {
          type uint64;
        }

        leaf merge {
          type uint64;
        }

        leaf copy {
          type uint64;
        }

        leaf free {
          type uint64;
        }

        leaf duplicate {
          type uint64;
        }

        leaf create {
          type uint64;
        }

        leaf serialize {
          type uint64;
        }

        leaf is-equal {
          type uint64;
        }

        leaf delete-unknown {
          type uint64;
        }

        leaf delete-field {
          type uint64;
        }

        leaf compare-keys {
          type uint64;
        }

        leaf set-field-msg {
          type uint64;
        }

        leaf set-field {
          type uint64;
        }

        leaf get-field {
          type uint64;
        }

        leaf get-field-txt {
          type uint64;
        }

        leaf has-field {
          type uint64;
        }

        leaf compare-fields {
          type uint64;
        }
      }

      container error-stats {

         rwpb:field-inline "true";
         description "Container for error statistics";

         leaf total_errors {
             type uint64;
         }
      }
    }
  }

  container pbc-ebuf {
    config "false";
    description "Container to export pbc error buffers from all the process";

    list tasklet {

      key "name";
      description "List to export per process global protobuf c error buffer";

      leaf name {
        type string;
        rwpb:field-inline "true";
        rwpb:field-string-max 256;
      }

      list error-records {
        description "Protobuf-c error records stored by time";
        max-elements 256;

        leaf time-stamp {
          type rwt:date-and-time;
          rwpb:field-inline "true";
          rwpb:field-string-max 64;
        }

        leaf error-str {
          type string;
          rwpb:field-inline "true";
          rwpb:field-string-max 256;
        }
      }
    }
  }
}
