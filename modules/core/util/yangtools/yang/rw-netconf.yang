/* STANDARD_RIFT_IO_COPYRIGHT */

/**
 * @file rw-netconf.yang
 * @author Vinod Kamalaraj
 * @date 2015/06/11
 * @brief RiftWare yang type overrides for netconf related operations
 *
 */
module rw-netconf
{
  namespace "http://riftio.com/ns/riftware-1.0/rw-netconf";
  prefix "rwnc";

  
  import ietf-netconf {
    prefix "nc";
    revision-date 2011-06-01;
  }
  
  import rw-yang-types {
    prefix "rwt";
  }


  description
   "This module contains redefinitions of the ietf-netconf, which allows
     customized extensions to be 
   defined for these types when used in RiftWare applications.";

  revision 2015-06-16 {
    description
      "Initial revision.";
    reference
      "RIFT yang types that redefine the IETF types.";
  }

    // As defined in RFC 6241 Appendix A
  typedef error-tag-type {
    type nc:error-tag-type;
  }

  typedef error-severity-type {
    type nc:error-severity-type;
  }

  grouping rpc-error {
    description "Netconf rpc-error element sent on rpc-reply";

    leaf error-type {
      description 
        "Defines the conceptual layer that the error occurred.";
      type error-type;
      //mandatory true;
    }

    leaf error-tag-type {
      description
        "Contains a string identifying the error condition.";
      type error-tag-type;
      //mandatory true;
    }

    // This is for future use
    leaf error-severity-type {
      description
        "Contains a string identifying the error severity, as
        determined by the device.";
      type error-severity-type;
    }

    leaf error-app-tag {
      description
        "Contains a string identifying the data-model-specific
        or implementation-specific error condition, if one exists.";
      type string;
    }

    leaf error-path {
      description
        "Contains the absolute XPath expression identifying
        the element path to the node that is associated with the error
        being reported in a particular rpc-error element.";
      type rwt:xpath1.0;
    }

    leaf error-message {
      description
        "Contains a string suitable for human display that
        describes the error condition. This element SHOULD include an 
        xml:lang attribute.";
      type string;
    }

    anyxml error-info {
      description
        "Contains protocol- or data-model-specific error content.
        This element will not be present if no such error content is
        provided for a particular error condition. 
        An implementation may include additional elements to 
        provide extended and/or implementation-specific debugging 
        information.";
    }
  }

  grouping rpc-error-reply {
    description "Netconf 'rpc-error' elements sent in 'rpc-reply'";

    list rpc-error {
      config false;
      uses rpc-error;
    }
  }

  
  //
  // Type definitions for rpc-error as per Netconf RFC 6241
  //
  
  typedef error-type {
    description "Netconf Error Type";
    type enumeration {
      enum transport;
      enum rpc;
      enum protocol;
      enum application;
    }
  }
}
