/* STANDARD_RIFT_IO_COPYRIGHT */
/**
 * @file rw-c-types.yang
 * @author Sujithra Periasamy
 * @date 2015/05/07
 * @brief RiftWare ctypes
 * 
 * Typedef's for riftware ctypes.
 */

module rw-c-types
{
  namespace "http://riftio.com/ns/riftware-1.0/rw-c-types";
  prefix "rwct";

  import rw-pb-ext { prefix "rwpb"; }
  rwpb:file-pbc-include "rwtypes.h";

  description
   "This module contains typedef's for rift ctypes.";

  revision 2015-05-07 {
    description
      "Initial revision.";
    reference
      "Typedef's for rift c-types";
  }

  typedef rw-ip-addr {
    rwpb:field-c-type "rw_ip_addr_t";
    type string;
  }

  typedef rw-ipv4-addr {
    rwpb:field-c-type "rw_ipV4_addr_t";
    type string;
  }

  typedef rw-ipv6-addr {
    rwpb:field-c-type "rw_ipV6_addr_t";
    type string;
  }

  typedef rw-ip-prefix {
    rwpb:field-c-type "rw_ip_prefix_t";
    type string;
  }

  typedef rw-ipv4-prefix {
    rwpb:field-c-type "rw_ip_prefix_t";
    type string;
  }

  typedef rw-ipv6-prefix {
    rwpb:field-c-type "rw_ip_prefix_t";
    type string;
  }

  typedef rw-mac-addr {
    rwpb:field-c-type "rw_mac_addr_t";
    type string;
  }

  typedef rw-callid {
    rwpb:field-c-type "rw_call_id_t";
    type string;
  }
}
