/* STANDARD_RIFT_IO_COPYRIGHT */

module test-py-gi-pb
{
  namespace "http://riftio.com/ns/core/util/yangtools/test/yang/town";
  prefix "test-py-gi-pb";

  import rw-pb-ext { prefix "rwpb"; }

  container top-bumpy {
    config false;
    list li1aa {
      leaf v { type string { length "0..4"; } }
      max-elements 3;

      list li2ab {
        leaf v { type string { length "0..4"; } }
        max-elements 3;

        container ct3ac {
          leaf v { type string { length "0..4"; } }
          list li4ad {
            leaf v { type string { length "0..4"; } }
            max-elements 3;
          }
          container ct5ae {
            leaf v { type string { length "0..4"; } }
          }
          container ct5af {
            leaf v { type string { length "0..4"; } }
          }
        }

        container ct3ag {
          leaf v { type string { length "0..4"; } }
          list li4ah {
            leaf v { type string { length "0..4"; } }
            max-elements 3;
          }
          container ct5ai {
            leaf v { type string { length "0..4"; } }
          }
          container ct5aj {
            leaf v { type string { length "0..4"; } }
          }
        }

        list li3ak {
          leaf v { type string { length "0..4"; } }
          max-elements 3;

          container ct4al {
            leaf v { type string { length "0..4"; } }
          }
          container ct4am {
            leaf v { type string { length "0..4"; } }
          }
        }
      }

      list li2bb {
        leaf v { type string { length "0..4"; } }
        max-elements 3;

        container ct3bc {
          leaf v { type string { length "0..4"; } }
          list li4bd {
            leaf v { type string { length "0..4"; } }
            max-elements 3;
          }
          container ct4be {
            leaf v { type string { length "0..4"; } }
          }
          container ct4bf {
            leaf v { type string { length "0..4"; } }
          }
        }

        list li3bk {
          leaf v { type string { length "0..4"; } }
          max-elements 3;

          container ct4bl {
            leaf v { type string { length "0..4"; } }
          }
          container ct4bm {
            leaf v { type string { length "0..4"; } }
          }
        }
      }

      container ct2cc {
        leaf v { type string { length "0..4"; } }
        list li3cd {
          leaf v { type string { length "0..4"; } }
          max-elements 3;
        }
        container ct3ce {
          leaf v { type string { length "0..4"; } }
        }
        container ct3cf {
          leaf v { type string { length "0..4"; } }
        }
      }

      container ct2cg {
        leaf v { type string { length "0..4"; } }
        list li3ch {
          leaf v { type string { length "0..4"; } }
          max-elements 3;
        }
        container ct3cj {
          leaf v { type string { length "0..4"; } }
        }
      }
    }

    container ct1dc {
      leaf v { type string { length "0..4"; } }
      list li2dd {
        leaf v { type string { length "0..4"; } }
        max-elements 3;
      }
      container ct2de {
        leaf v { type string { length "0..4"; } }
      }
    }

    container ct1dg {
      leaf v { type string { length "0..4"; } }
      container ct2di {
        leaf v { type string { length "0..4"; } }
      }
      container ct2dj {
        leaf v { type string { length "0..4"; } }
      }
    }

    list li1ek {
      leaf v { type string { length "0..4"; } }
      max-elements 3;

      container ct2el {
        leaf v { type string { length "0..4"; } }
      }
    }

    list li1fa {
      leaf v { type string { length "0..4"; } }
      max-elements 3;

      list li2fb {
        leaf v { type string { length "0..4"; } }
        max-elements 3;

        list li3fc {
          leaf v { type string { length "0..4"; } }
          max-elements 3;
        }
      }
    }
  }

  container top-flat {
    config false;
    rwpb:msg-flat true;
    list li1aa {
      leaf v { type string { length "0..4"; } }
      max-elements 3;

      list li2ab {
        leaf v { type string { length "0..4"; } }
        max-elements 3;

        container ct3ac {
          leaf v { type string { length "0..4"; } }
          list li4ad {
            leaf v { type string { length "0..4"; } }
            max-elements 3;
          }
          container ct5ae {
            leaf v { type string { length "0..4"; } }
          }
          container ct5af {
            leaf v { type string { length "0..4"; } }
          }
        }

        container ct3ag {
          leaf v { type string { length "0..4"; } }
          list li4ah {
            leaf v { type string { length "0..4"; } }
            max-elements 3;
          }
          container ct5ai {
            leaf v { type string { length "0..4"; } }
          }
          container ct5aj {
            leaf v { type string { length "0..4"; } }
          }
        }

        list li3ak {
          leaf v { type string { length "0..4"; } }
          max-elements 3;

          container ct4al {
            leaf v { type string { length "0..4"; } }
          }
          container ct4am {
            leaf v { type string { length "0..4"; } }
          }
        }
      }

      list li2bb {
        leaf v { type string { length "0..4"; } }
        max-elements 3;

        container ct3bc {
          leaf v { type string { length "0..4"; } }
          list li4bd {
            leaf v { type string { length "0..4"; } }
            max-elements 3;
          }
          container ct4be {
            leaf v { type string { length "0..4"; } }
          }
          container ct4bf {
            leaf v { type string { length "0..4"; } }
          }
        }

        list li3bk {
          leaf v { type string { length "0..4"; } }
          max-elements 3;

          container ct4bl {
            leaf v { type string { length "0..4"; } }
          }
          container ct4bm {
            leaf v { type string { length "0..4"; } }
          }
        }
      }

      container ct2cc {
        leaf v { type string { length "0..4"; } }
        list li3cd {
          leaf v { type string { length "0..4"; } }
          max-elements 3;
        }
        container ct3ce {
          leaf v { type string { length "0..4"; } }
        }
        container ct3cf {
          leaf v { type string { length "0..4"; } }
        }
      }

      container ct2cg {
        leaf v { type string { length "0..4"; } }
        list li3ch {
          leaf v { type string { length "0..4"; } }
          max-elements 3;
        }
        container ct3cj {
          leaf v { type string { length "0..4"; } }
        }
      }
    }

    container ct1dc {
      leaf v { type string { length "0..4"; } }
      list li2dd {
        leaf v { type string { length "0..4"; } }
        max-elements 3;
      }
      container ct2de {
        leaf v { type string { length "0..4"; } }
      }
    }

    container ct1dg {
      leaf v { type string { length "0..4"; } }
      container ct2di {
        leaf v { type string { length "0..4"; } }
      }
      container ct2dj {
        leaf v { type string { length "0..4"; } }
      }
    }

    list li1ek {
      leaf v { type string { length "0..4"; } }
      max-elements 3;

      container ct2el {
        leaf v { type string { length "0..4"; } }
      }
    }

    list li1fa {
      leaf v { type string { length "0..4"; } }
      max-elements 3;

      list li2fb {
        leaf v { type string { length "0..4"; } }
        max-elements 3;

        list li3fc {
          leaf v { type string { length "0..4"; } }
          max-elements 3;
        }
      }
    }
  }

  container top-cont-inl {
    config false;
    list li1aa {
      leaf v { type string { length "0..4"; } }
      max-elements 3;

      list li2ab {
        leaf v { type string { length "0..4"; } }
        max-elements 3;

        container ct3ac {
          leaf v { type string { length "0..4"; } }
          rwpb:field-inline true;
          list li4ad {
            leaf v { type string { length "0..4"; } }
            max-elements 3;
          }
          container ct5ae {
            rwpb:field-inline true;
            leaf v { type string { length "0..4"; } }
          }
          container ct5af {
            rwpb:field-inline true;
            leaf v { type string { length "0..4"; } }
          }
        }

        container ct3ag {
          leaf v { type string { length "0..4"; } }
          rwpb:field-inline true;
          list li4ah {
            leaf v { type string { length "0..4"; } }
            max-elements 3;
          }
          container ct5ai {
            rwpb:field-inline true;
            leaf v { type string { length "0..4"; } }
          }
          container ct5aj {
            rwpb:field-inline true;
            leaf v { type string { length "0..4"; } }
          }
        }

        list li3ak {
          leaf v { type string { length "0..4"; } }
          max-elements 3;

          container ct4al {
            rwpb:field-inline true;
            leaf v { type string { length "0..4"; } }
          }
          container ct4am {
            rwpb:field-inline true;
            leaf v { type string { length "0..4"; } }
          }
        }
      }

      list li2bb {
        leaf v { type string { length "0..4"; } }
        max-elements 3;

        container ct3bc {
          leaf v { type string { length "0..4"; } }
          rwpb:field-inline true;
          list li4bd {
            leaf v { type string { length "0..4"; } }
            max-elements 3;
          }
          container ct4be {
            rwpb:field-inline true;
            leaf v { type string { length "0..4"; } }
          }
          container ct4bf {
            rwpb:field-inline true;
            leaf v { type string { length "0..4"; } }
          }
        }

        list li3bk {
          leaf v { type string { length "0..4"; } }
          max-elements 3;

          container ct4bl {
            rwpb:field-inline true;
            leaf v { type string { length "0..4"; } }
          }
          container ct4bm {
            rwpb:field-inline true;
            leaf v { type string { length "0..4"; } }
          }
        }
      }

      container ct2cc {
        leaf v { type string { length "0..4"; } }
        rwpb:field-inline true;
        list li3cd {
          leaf v { type string { length "0..4"; } }
          max-elements 3;
        }
        container ct3ce {
          rwpb:field-inline true;
          leaf v { type string { length "0..4"; } }
        }
        container ct3cf {
          rwpb:field-inline true;
          leaf v { type string { length "0..4"; } }
        }
      }

      container ct2cg {
        leaf v { type string { length "0..4"; } }
        rwpb:field-inline true;
        list li3ch {
          leaf v { type string { length "0..4"; } }
          max-elements 3;
        }
        container ct3cj {
          rwpb:field-inline true;
          leaf v { type string { length "0..4"; } }
        }
      }
    }

    container ct1dc {
      leaf v { type string { length "0..4"; } }
      rwpb:field-inline true;
      list li2dd {
        leaf v { type string { length "0..4"; } }
        max-elements 3;
      }
      container ct2de {
        rwpb:field-inline true;
        leaf v { type string { length "0..4"; } }
      }
    }

    container ct1dg {
      leaf v { type string { length "0..4"; } }
      rwpb:field-inline true;
      container ct2di {
        rwpb:field-inline true;
        leaf v { type string { length "0..4"; } }
      }
      container ct2dj {
        rwpb:field-inline true;
        leaf v { type string { length "0..4"; } }
      }
    }

    list li1ek {
      leaf v { type string { length "0..4"; } }
      max-elements 3;

      container ct2el {
        rwpb:field-inline true;
        leaf v { type string { length "0..4"; } }
      }
    }

    list li1fa {
      leaf v { type string { length "0..4"; } }
      max-elements 3;

      list li2fb {
        leaf v { type string { length "0..4"; } }
        max-elements 3;

        list li3fc {
          leaf v { type string { length "0..4"; } }
          max-elements 3;
        }
      }
    }
  }

  container top-list-inl {
    config false;
    list li1aa {
      rwpb:field-inline true;
      leaf v { type string { length "0..4"; } }
      max-elements 3;

      list li2ab {
        rwpb:field-inline true;
        leaf v { type string { length "0..4"; } }
        max-elements 3;

        container ct3ac {
          leaf v { type string { length "0..4"; } }
          list li4ad {
            rwpb:field-inline true;
            leaf v { type string { length "0..4"; } }
            max-elements 3;
          }
          container ct5ae {
            leaf v { type string { length "0..4"; } }
          }
          container ct5af {
            leaf v { type string { length "0..4"; } }
          }
        }

        container ct3ag {
          leaf v { type string { length "0..4"; } }
          list li4ah {
            rwpb:field-inline true;
            leaf v { type string { length "0..4"; } }
            max-elements 3;
          }
          container ct5ai {
            leaf v { type string { length "0..4"; } }
          }
          container ct5aj {
            leaf v { type string { length "0..4"; } }
          }
        }

        list li3ak {
          rwpb:field-inline true;
          leaf v { type string { length "0..4"; } }
          max-elements 3;

          container ct4al {
            leaf v { type string { length "0..4"; } }
          }
          container ct4am {
            leaf v { type string { length "0..4"; } }
          }
        }
      }

      list li2bb {
        rwpb:field-inline true;
        leaf v { type string { length "0..4"; } }
        max-elements 3;

        container ct3bc {
          leaf v { type string { length "0..4"; } }
          list li4bd {
            rwpb:field-inline true;
            leaf v { type string { length "0..4"; } }
            max-elements 3;
          }
          container ct4be {
            leaf v { type string { length "0..4"; } }
          }
          container ct4bf {
            leaf v { type string { length "0..4"; } }
          }
        }

        list li3bk {
          rwpb:field-inline true;
          leaf v { type string { length "0..4"; } }
          max-elements 3;

          container ct4bl {
            leaf v { type string { length "0..4"; } }
          }
          container ct4bm {
            leaf v { type string { length "0..4"; } }
          }
        }
      }

      container ct2cc {
        leaf v { type string { length "0..4"; } }
        list li3cd {
          rwpb:field-inline true;
          leaf v { type string { length "0..4"; } }
          max-elements 3;
        }
        container ct3ce {
          leaf v { type string { length "0..4"; } }
        }
        container ct3cf {
          leaf v { type string { length "0..4"; } }
        }
      }

      container ct2cg {
        leaf v { type string { length "0..4"; } }
        list li3ch {
          rwpb:field-inline true;
          leaf v { type string { length "0..4"; } }
          max-elements 3;
        }
        container ct3cj {
          leaf v { type string { length "0..4"; } }
        }
      }
    }

    container ct1dc {
      leaf v { type string { length "0..4"; } }
      list li2dd {
        rwpb:field-inline true;
        leaf v { type string { length "0..4"; } }
        max-elements 3;
      }
      container ct2de {
        leaf v { type string { length "0..4"; } }
      }
    }

    container ct1dg {
      leaf v { type string { length "0..4"; } }
      container ct2di {
        leaf v { type string { length "0..4"; } }
      }
      container ct2dj {
        leaf v { type string { length "0..4"; } }
      }
    }

    list li1ek {
      rwpb:field-inline true;
      leaf v { type string { length "0..4"; } }
      max-elements 3;

      container ct2el {
        leaf v { type string { length "0..4"; } }
      }
    }

    list li1fa {
      rwpb:field-inline true;
      leaf v { type string { length "0..4"; } }
      max-elements 3;

      list li2fb {
        rwpb:field-inline true;
        leaf v { type string { length "0..4"; } }
        max-elements 3;

        list li3fc {
          rwpb:field-inline true;
          leaf v { type string { length "0..4"; } }
          max-elements 3;
        }
      }
    }
  }

  container top-even-inl {
    config false;
    list li1aa {
      leaf v { type string { length "0..4"; } }
      max-elements 3;

      list li2ab {
        rwpb:field-inline true;
        leaf v { type string { length "0..4"; } }
        max-elements 3;

        container ct3ac {
          leaf v { type string { length "0..4"; } }
          list li4ad {
            rwpb:field-inline true;
            leaf v { type string { length "0..4"; } }
            max-elements 3;
          }
          container ct5ae {
            leaf v { type string { length "0..4"; } }
          }
          container ct5af {
            leaf v { type string { length "0..4"; } }
          }
        }

        container ct3ag {
          leaf v { type string { length "0..4"; } }
          list li4ah {
            rwpb:field-inline true;
            leaf v { type string { length "0..4"; } }
            max-elements 3;
          }
          container ct5ai {
            leaf v { type string { length "0..4"; } }
          }
          container ct5aj {
            leaf v { type string { length "0..4"; } }
          }
        }

        list li3ak {
          leaf v { type string { length "0..4"; } }
          max-elements 3;

          container ct4al {
            rwpb:field-inline true;
            leaf v { type string { length "0..4"; } }
          }
          container ct4am {
            rwpb:field-inline true;
            leaf v { type string { length "0..4"; } }
          }
        }
      }

      list li2bb {
        rwpb:field-inline true;
        leaf v { type string { length "0..4"; } }
        max-elements 3;

        container ct3bc {
          leaf v { type string { length "0..4"; } }
          list li4bd {
            rwpb:field-inline true;
            leaf v { type string { length "0..4"; } }
            max-elements 3;
          }
          container ct4be {
            rwpb:field-inline true;
            leaf v { type string { length "0..4"; } }
          }
          container ct4bf {
            rwpb:field-inline true;
            leaf v { type string { length "0..4"; } }
          }
        }

        list li3bk {
          leaf v { type string { length "0..4"; } }
          max-elements 3;

          container ct4bl {
            rwpb:field-inline true;
            leaf v { type string { length "0..4"; } }
          }
          container ct4bm {
            rwpb:field-inline true;
            leaf v { type string { length "0..4"; } }
          }
        }
      }

      container ct2cc {
        rwpb:field-inline true;
        leaf v { type string { length "0..4"; } }
        list li3cd {
          leaf v { type string { length "0..4"; } }
          max-elements 3;
        }
        container ct3ce {
          leaf v { type string { length "0..4"; } }
        }
        container ct3cf {
          leaf v { type string { length "0..4"; } }
        }
      }

      container ct2cg {
        rwpb:field-inline true;
        leaf v { type string { length "0..4"; } }
        list li3ch {
          leaf v { type string { length "0..4"; } }
          max-elements 3;
        }
        container ct3cj {
          leaf v { type string { length "0..4"; } }
        }
      }
    }

    container ct1dc {
      leaf v { type string { length "0..4"; } }
      list li2dd {
        rwpb:field-inline true;
        leaf v { type string { length "0..4"; } }
        max-elements 3;
      }
      container ct2de {
        rwpb:field-inline true;
        leaf v { type string { length "0..4"; } }
      }
    }

    container ct1dg {
      leaf v { type string { length "0..4"; } }
      container ct2di {
        rwpb:field-inline true;
        leaf v { type string { length "0..4"; } }
      }
      container ct2dj {
        rwpb:field-inline true;
        leaf v { type string { length "0..4"; } }
      }
    }

    list li1ek {
      leaf v { type string { length "0..4"; } }
      max-elements 3;

      container ct2el {
        rwpb:field-inline true;
        leaf v { type string { length "0..4"; } }
      }
    }

    list li1fa {
      leaf v { type string { length "0..4"; } }
      max-elements 3;

      list li2fb {
        rwpb:field-inline true;
        leaf v { type string { length "0..4"; } }
        max-elements 3;

        list li3fc {
          leaf v { type string { length "0..4"; } }
          max-elements 3;
        }
      }
    }
  }

  container top-odd-inl {
    config false;
    list li1aa {
      rwpb:field-inline true;
      leaf v { type string { length "0..4"; } }
      max-elements 3;

      list li2ab {
        leaf v { type string { length "0..4"; } }
        max-elements 3;

        container ct3ac {
          rwpb:field-inline true;
          leaf v { type string { length "0..4"; } }
          list li4ad {
            leaf v { type string { length "0..4"; } }
            max-elements 3;
          }
          container ct5ae {
            rwpb:field-inline true;
            leaf v { type string { length "0..4"; } }
          }
          container ct5af {
            rwpb:field-inline true;
            leaf v { type string { length "0..4"; } }
          }
        }

        container ct3ag {
          rwpb:field-inline true;
          leaf v { type string { length "0..4"; } }
          list li4ah {
            leaf v { type string { length "0..4"; } }
            max-elements 3;
          }
          container ct5ai {
            rwpb:field-inline true;
            leaf v { type string { length "0..4"; } }
          }
          container ct5aj {
            rwpb:field-inline true;
            leaf v { type string { length "0..4"; } }
          }
        }

        list li3ak {
          rwpb:field-inline true;
          leaf v { type string { length "0..4"; } }
          max-elements 3;

          container ct4al {
            leaf v { type string { length "0..4"; } }
          }
          container ct4am {
            leaf v { type string { length "0..4"; } }
          }
        }
      }

      list li2bb {
        leaf v { type string { length "0..4"; } }
        max-elements 3;

        container ct3bc {
          rwpb:field-inline true;
          leaf v { type string { length "0..4"; } }
          list li4bd {
            leaf v { type string { length "0..4"; } }
            max-elements 3;
          }
          container ct4be {
            leaf v { type string { length "0..4"; } }
          }
          container ct4bf {
            leaf v { type string { length "0..4"; } }
          }
        }

        list li3bk {
          rwpb:field-inline true;
          leaf v { type string { length "0..4"; } }
          max-elements 3;

          container ct4bl {
            leaf v { type string { length "0..4"; } }
          }
          container ct4bm {
            leaf v { type string { length "0..4"; } }
          }
        }
      }

      container ct2cc {
        leaf v { type string { length "0..4"; } }
        list li3cd {
          rwpb:field-inline true;
          leaf v { type string { length "0..4"; } }
          max-elements 3;
        }
        container ct3ce {
          rwpb:field-inline true;
          leaf v { type string { length "0..4"; } }
        }
        container ct3cf {
          rwpb:field-inline true;
          leaf v { type string { length "0..4"; } }
        }
      }

      container ct2cg {
        leaf v { type string { length "0..4"; } }
        list li3ch {
          rwpb:field-inline true;
          leaf v { type string { length "0..4"; } }
          max-elements 3;
        }
        container ct3cj {
          rwpb:field-inline true;
          leaf v { type string { length "0..4"; } }
        }
      }
    }

    container ct1dc {
      rwpb:field-inline true;
      leaf v { type string { length "0..4"; } }
      list li2dd {
        leaf v { type string { length "0..4"; } }
        max-elements 3;
      }
      container ct2de {
        leaf v { type string { length "0..4"; } }
      }
    }

    container ct1dg {
      rwpb:field-inline true;
      leaf v { type string { length "0..4"; } }
      container ct2di {
        leaf v { type string { length "0..4"; } }
      }
      container ct2dj {
        leaf v { type string { length "0..4"; } }
      }
    }

    list li1ek {
      rwpb:field-inline true;
      leaf v { type string { length "0..4"; } }
      max-elements 3;

      container ct2el {
        leaf v { type string { length "0..4"; } }
      }
    }

    list li1fa {
      rwpb:field-inline true;
      leaf v { type string { length "0..4"; } }
      max-elements 3;

      list li2fb {
        leaf v { type string { length "0..4"; } }
        max-elements 3;

        list li3fc {
          rwpb:field-inline true;
          leaf v { type string { length "0..4"; } }
          max-elements 3;
        }
      }
    }
  }
}
