/*
 * STANDARD_RIFT_IO_COPYRIGHT
 *
 */

module ifmgr {
  namespace "http://riftio.com/ns/riftware-1.0/rw-ifmgr-data";
  prefix "ifmgr";

  import rw-base-f {
    prefix rwbase;
  }
  import rw-pb-ext {
    prefix "rwpb";
  }

  description "Test yang module";
  revision 2014-05-27 {
    description "Initial version"; 
  }

  augment /rwbase:colony {
    list port-state {
      rwpb:msg-new PortState;
      key "portno";
      leaf portno {
        type uint16;
      }
    }
  }
}
