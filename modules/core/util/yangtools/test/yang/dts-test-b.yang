/* STANDARD_RIFT_IO_COPYRIGHT */

/**
 * @file dts-test-b.yang
 * @author Rajesh Velandy
 * @date 2014/08/08
 * @brief Top-level yang for testing libncx.
 */

module dts-test-b
{
  namespace "http://riftio.com/ns/core/rwvx/rwdts/test/yang";
  prefix "ps";

  import rw-pb-ext { prefix "rwpb"; }

  description
    "This yang models a person";

  revision 2014-03-05 {
    description "Initial version"; }

  typedef phone-type {
    type enumeration {
              enum MOBILE { value 0; }
              enum HOME   { value 1; }
              enum WORK   { value 2; }
    }
  }
  container person {
    rwpb:msg-new Person;

    leaf name         { type string; }
    leaf id           { type int32; }
    leaf email        { type string; }
    leaf employed     { type boolean; }


    list phone {
        key "number";
        rwpb:msg-new PhoneNumber;

        leaf number { type string; }
        leaf type  { type phone-type;}
    }

    container emergency-phone {
      rwpb:msg-new PhoneNumber1;

      leaf number { type string; }
      leaf type  { type phone-type;}
    }
  }

  container flat-person {
    rwpb:msg-new FlatPerson;
    rwpb:msg-flat "true";

    leaf name         { type string; rwpb:field-string-max "64"; }
    leaf id           { type int32; }
    leaf email        { type string; rwpb:field-string-max "64"; }
    leaf employed     { type boolean; }

    list phone {
        key "number";
        rwpb:field-inline-max "64";
        rwpb:msg-new FlatPhoneNumber;
        rwpb:msg-flat "true";

        leaf number { type string; rwpb:field-string-max "64"; }
        leaf type  { type phone-type; }
    }
    container emergency-phone {
      rwpb:msg-new FlatPhoneNumber1;
      rwpb:msg-flat "true";

      leaf number { type string; rwpb:field-string-max "64"; }
      leaf type  { type phone-type; }
    }
  }
}
