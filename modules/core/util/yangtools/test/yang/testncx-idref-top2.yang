/* STANDARD_RIFT_IO_COPYRIGHT */

/**
 * @file testncx-idref-top2.yang
 * @author Rajesh Velandy
 * @date 2014/04/03
 * @brief yangncx test file for Identity References
 */

module testncx-idref-top2
{
  namespace "http://riftio.com/ns/core/util/yangtools/tests/testncx-idref-top2";
  prefix "tnx-id-top2";

  import testncx-idref-base1 { prefix "tnx-id-base1"; }  // Give it a different prefix

  description "Module testing for yangncxi Idref";
  revision 2014-04-03 { description "Initial version"; }

  identity french {
    base tnx-id-base1:language;
    description "The Language French";
  }

  identity malayalam {
    base tnx-id-base1:language;
    description "The Language Malayalam";
  }

  leaf language-name {
    type union {
      type identityref { base "tnx-id-base1:language"; }
    }
  }
}
