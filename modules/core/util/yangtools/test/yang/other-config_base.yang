/*
 * STANDARD_RIFT_IO_COPYRIGHT
 *
 */

module other-config_base
{
  namespace "http://riftio.com/ns/riftware-1.0/other-config_base";
  prefix "config";

  import rw-pb-ext {
    prefix "rwpb";
  }

  import rw-yang-types {
    prefix rwt;
  }

  import rw-cli-ext {
    prefix "rwcli";
  }

  revision 2013-03-21 {
    description
      "Initial revision.";
    reference
      "RIFT IPSec Datatypes";
  }

  container config {
    rwpb:msg-new Config;
    uses service-realm;
  }

  grouping service-realm { 
    list service-realm {
      rwpb:msg-new ConfigServiceRealm;
      key "name";
      leaf name {
        type string;
      }
      uses vpn-context;
      uses port;
    }
  } // grouping service-realm

  grouping vpn-context {
    list vpn-context {
      rwpb:msg-new ConfigVpnContext;
      key "name";
      leaf name {
        type string;
      }
      list ip-interface-group {
        rwpb:msg-new ConfigIpInterfaceGroup;
        key name;
        leaf name {
          type string;
        }
        list ip-interface {
          rwpb:msg-new ConfigIpInterface;
          key name;
          leaf name {
            type string;
          }
          leaf address {
            type rwt:ip-prefix;
          }
        }
        container bind {
          leaf ipsec-policy {
            type string;
          }
        }
      }
    }
  } // grouping vpn-context

  grouping port {
    container port {
      rwpb:msg-new ConfigPort;
      list ethernet {
        rwcli:new-mode "ethernet";
        key name;
        leaf name {
          type string;
        }
        container bind {
          leaf ip-interface {
            type leafref {
              path "/config/service-realm/vpn-context/ip-interface-group/ip-interface/name";
            }
          }
        }
      }
    }
  } // grouping port

  container save {
    config false;
    description "save data";
    container config {
      description "save the configuration to a file";
      container text {
        description "save configuration in text mode";
        leaf filename {
          type string;
        }
      } 
      container fooxml {
        description "save configuration in xml mode";
        leaf filename {
          type string;
        }
      }
    }
  }

  container show {
    description "show operational state";
    config false;
    container config {
      description "show configuration";
      leaf text {
        type empty;
        description "show configuration in text mode";                
      }
      leaf fooxml {
        type empty;
        description "show configuration in xml mode";
      }
    }
    container cli {
      description "show cli specific information";
      leaf history {
        type empty;
        description "show history of CLI commands";                
      }
      container manifest {
        description "show manifests loaded for this cli";
        
        leaf list {        
          type empty;
          description "display the list of all loaded";
        }
        leaf name {
          type string;
          description "display details of the named manifest";
        }

      }
    }
  }

  container help {
    description "show help for commands";
    config false;
    container command {
      description "command for which help is requested";
      leaf name {
        type string;
        description "name of command";
        mandatory true;
      }
    }
  }
  
  container commit { 
    config false;
    description "commit the configuration";
  }

  container clear { 
    config false;
    description "clear the configuration";
    container cli {
      description "clear data associated with CLI";
      leaf history {
        description "clear the current CLI history";
        type empty;
      }
    }
  }

  container start { 
    config false;
    description "start";
  }

} // module other-config_base
