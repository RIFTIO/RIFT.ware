/* STANDARD_RIFT_IO_COPYRIGHT */

/**
 * @file rw-composite.yang
 * @author Vinod Kamalaraj
 * @date 2014/10/1
 * @brief A compsite YANG file that imports all other modules loaded by
 * rwuagent. This YANG file gives the uagent a global schema view
 */

module rw-composite-d
{
  namespace "http://riftio.com/ns/riftware-1.0/rw-composite";
  prefix "rwcomp";

  import rw-base-d { prefix rw-base; }
  import rw-fpath-d { prefix rw-fpath; }
  import rwuagent-cli-d { prefix rwuagent-cli; }
  import rw-appmgr-d { prefix rw-appmgr; }
  import rw-appmgr-log-d { prefix rw-appmgr-log; }
  import rwmanifest-d { prefix rwmanifest; }
  import rw-vcs-d { prefix rw-vcs; }
  import rwlog-mgmt-d { prefix rwlog-mgmt; }
  import rw-3gpp-types-d { prefix rw-3gpp-types; }
  import rwdts-data-d { prefix rwdts-data; }
  import rw-dts-api-log-d { prefix rw-dts-api-log; }
  import rw-dts-router-log-d { prefix rw-dts-router-log; }
  import rwmsg-data-d { prefix rwmsg-data; }
  import rw-fpath-log-d { prefix rw-fpath-log; }
  import rw-ipsec-d { prefix rw-ipsec; }

  description "RW Composite Yang";
  revision 2014-10-01 {
    description "Initial version"; 
  }
}
