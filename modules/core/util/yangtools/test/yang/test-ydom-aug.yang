/* STANDARD_RIFT_IO_COPYRIGHT */

/**
 * @file test-ydom-aug.yang
 * @author Tom Seidenberg
 * @date 2014/05/15
 */

module test-ydom-aug
{
  namespace "http://riftio.com/ns/yangtools/test-ydom-aug";
  prefix "a";

  import test-ydom-top { prefix "t"; }

  description "Augmenting yang for XMLManagerYang testing";
  revision 2014-05-15 { description "Created from test-ydom-top"; }

  augment /t:top/t:apis_test {
    description "for test RwYangDom.ApiTest";
    leaf aint8 { type int8; }
    leaf astring { type string; }
    leaf aempty { type empty; }
    /* With the latest yuma patch update, this is not compiling and hence commented out */
    /* leaf alref { type leafref { path "../t:leaflist"; } } */
  }
}
