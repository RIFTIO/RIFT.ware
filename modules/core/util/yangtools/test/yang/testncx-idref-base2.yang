/* STANDARD_RIFT_IO_COPYRIGHT */

/**
 * @file testncx-idref-base2.yang
 * @author Rajesh Velandy
 * @date 2014/04/03
 * @brief yangncx test file for Identity References
 */

module testncx-idref-base2
{
  namespace "http://riftio.com/ns/core/util/yangtools/tests/testncx-idref-base2";
  prefix "tnx-id-b2";

  import testncx-idref-base1 { prefix "tnxid-base1"; }  // Give it a different prefix

  description "Module testing for yangncxi Idref";
  revision 2014-04-03 { description "Initial version"; }

  identity telugu {
    base tnxid-base1:language;
    description "The Language Telugu";
  }
}
