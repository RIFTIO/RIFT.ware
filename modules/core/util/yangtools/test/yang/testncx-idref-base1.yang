/* STANDARD_RIFT_IO_COPYRIGHT */

/**
 * @file testncx-idref-base1.yang
 * @author Rajesh Velandy
 * @date 2014/04/03
 * @brief yangncx test file for Identity References
 */

module testncx-idref-base1
{
  namespace "http://riftio.com/ns/core/util/yangtools/tests/testncx-idref-base1";
  prefix "tnx-id-b1";

  description "Module testing for yangncxi Idref";
  revision 2014-04-03 { description "Initial version"; }

  identity language {
    description "A Language";
  }

  identity english {
    base language;
    description "The Language English";
  }
  
}
