/*
 * STANDARD_RIFT_IO_COPYRIGHT
 *
 */

module rw-vcs-d
{
  namespace "http://riftio.com/ns/riftware-1.0/rw-vcs";
  prefix "rw-vcs";

  import rw-notify-ext-d {
    prefix "rwnotify";
  }

  import rw-pb-ext {
    prefix "rwpb";
  }

  import rw-log-d {
    prefix "rwlog";
  }

  import rw-base-d {
    prefix "rwbase";
  }

  revision 2014-10-22 {
    description "Initial revision";
    reference "RIFT Virtual Container System";
  }

  augment /rwbase:tasklet {
    container vcs-cont {
      leaf component-name {
        type string;
      }
    }
  }

  augment /rwbase:tasklet/rwbase:info/rwbase:components/rwbase:component_info/rwbase:component_info {
    case colony-info {

      leaf colony-name {
        type string;
      }

      leaf number-vms {
        type uint32;
      }
    }
  }

  // Shitty names are because fpath defines the same RPCs and the CLI doesn't
  // understand namespaces.
  rpc vstart {
    input {
      leaf component-name {
        description "Name of the component to create a new instance of";
        type string;
        mandatory true;
      }

      leaf parent-instance {
        description "Instance-name of the parent of the new instance";
        type string;
        mandatory true;
      }
    }

    output {
      leaf rw_status {
        description "Return status of the start operation";
        type uint32;
      }

      leaf instance-name {
        description "On success, the instance-name of the started component";
        type string;
      }
    }
  }

  rpc vstop {
    input {
      leaf instance-name {
        description "Instance-name of instance to stop";
        type string;
        mandatory true;
      }
    }

    output {
      leaf rw_status {
        description "Return status of the start operation";
        type uint32;
      }
    }
  }

  // VCS notification event-ids are numbered 10xxx
  notification vtasklet_start {
    rwnotify:log-event-id 00010000;
    description "Tasklet started";
    uses rwlog:severity-info;

    leaf tasklet-name {
      type string;
      description "Tasklet name";
    }

    leaf tasklet-instance {
      type uint32;
      description "Tasklet instance";
    }
  }

  notification core_reporter_starting {
    rwnotify:log-event-id 00010001;
    rwpb:msg-new "CoreReporterStarting";
    description "Core report scanner starting";
    uses rwlog:severity-debug;
    leaf coredir {
      type string;
      description "Scan directory";
    }
  }

  notification core_found {
    rwnotify:log-event-id 00010002;
    rwpb:msg-new "CoreFound";
    description "Core file found";
    uses rwlog:severity-error;
    leaf corefile {
      type string;
      description "Core filename";
    }
    leaf coredesc {
      type string;
      description "Core description";
    }
    leaf coretime {
      type string;
      description "Core timestamp";
    }
  }

}
