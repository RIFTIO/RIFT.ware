/* STANDARD_RIFT_IO_COPYRIGHT */

/**
 * @file rw-appmgr.yang
 * @author Aniruddha Atale
 * @date 08/11/2014
 * @brief RiftWare CLI for FastPath Controller
 */

module rw-appmgr-b
{
  namespace "urn:ietf:params:xml:ns:yang:rift:config";
  prefix "rwappmgr";

  import rw-base-b {
    prefix rwbase;
  }

  import rw-cli-ext { 
    prefix "rwcli";
  }

  import rw-pb-ext {
    prefix "rwpb";
  }

  import rw-yang-types {
    prefix "rwt";
  }

  revision 2014-08-11 {
    description
      "Initial revision.";
    reference
      "RIFT Application Manager";
  }

  typedef trafsim-proto-type {
    description "Protocol to be simulated";
    type enumeration {
      enum diameter;
      enum radius;
      enum pktgen;
    }
  }

  typedef trafsim-operation-mode {
    description "Trafsim mode of operation";
    type enumeration {
      enum server;
      enum client;
    }
  }

  typedef diameter-interface-type {
    description "Diameter Interface";
    type enumeration {
      enum Gx;
      enum Gy;
      enum Rf;
    }
  }

  grouping bind-info {
    container network-context {
      description "network context name";
      leaf name {
        type string;
        rwpb:field-inline "true";
        rwpb:field-string-max 64;
      }
    }
    
    leaf ip-address {
      description "Listen IP address";
      type rwt:ip-address;
      rwpb:field-string-max 46;
      rwpb:field-inline "true";
    }
    leaf port {
      description "Listen port";
      type uint16;
      default "3868";
    }
    leaf instances-per-vm {
      description "Maximum external application instances per VM";
      type uint32;
      default "4";
    }
    leaf number-of-vm {
      description "Total VM in colony running external application";
      type uint32;
    }    

  }

  grouping diameter-interface-selection {
    choice diameter-interface-type {
      case Gx {
        leaf Gx {
          description "Gx interface";
          type empty;
        }
      }
      case Gy {
        leaf Gy {
          description "Gy interface";
          type empty;
        }
      }
      case Rf {
        leaf Rf {
          description "Rf interface";
          type empty;
        }
      }
    }
  }
  
  augment /rwbase:colony {

    list trafsim-service {
      description "Trafsim Service";
      rwcli:new-mode "trafsim-service";
      max-elements 8;

      key "name";

      leaf name {
        description "Name of trafsim service";
        rwpb:field-inline "true";
        rwpb:field-string-max 64;
        type string;
      }
      container protocol-mode {
        description "Trafsim Protocol Type";
        choice trafsim-proto-type {
          case diameter {
            container diameter-sim {
              rwcli:new-mode "diameter-sim";
              rwpb:msg-new DiameterSim;
              container operational-mode {
                choice trafsim-operation-mode {
                  case server {
                    container diameter-server {
                      rwcli:new-mode "diameter-server";
                      rwpb:msg-new DiameterServer;
                      container diameter-interface {
                        uses diameter-interface-selection;
                      }
                      uses bind-info;
                    }
                  } // case server
                  case client {
                    container diameter-client {
                      rwcli:new-mode "diameter-client";
                      rwpb:msg-new DiameterClient;
                      container diameter-interface {
                        uses diameter-interface-selection;
                      }
                      uses bind-info;
                      leaf server-address {
                        description "Server IP address";
                        type rwt:ip-address;
                        rwpb:field-inline "true";
                        rwpb:field-string-max 46;
                      }
                      leaf server-port {
                        description "Server port";
                        type uint16;
                      }
                      leaf call-rate {
                        description "Call-Rate";
                        type uint32;
                      }
                    } // container diameter-client
                  } // case client
                } // choice trafsim-operation-mode
              } // container operational mode
            } // container diameter-sim
          } // case diameter
          case radius {
            container radius-sim {
              rwcli:new-mode "radius-sim";
              rwpb:msg-new RadiusSim;

              choice trafsim-operation-mode {
                case server {
                  rwcli:new-mode "radius-server";
                
                } // case server
                case client {
                  rwcli:new-mode "radius-client";
                } // case client
              
              } //choice trafsim-operation-mode
            } // container radius-sim         
          } // case radius

          case pktgen {
            container pktgen-sim {
              rwcli:new-mode "pktgen-sim";
              rwpb:msg-new PktgenSim;
              //rwpb:msg-flat true;

              container network-context {
                description "network context name";
                leaf name {
                  type string;
                  rwpb:field-inline "true";
                  rwpb:field-string-max 64;
                }
              }
              leaf instances-per-vm {
                description "Maximum external application instances per VM";
                type uint32;
                default "4";
              }
              leaf number-of-vm {
                description "Total VM in colony running external application";
                type uint32;
              }    
              leaf test-file-name {
                type string;
                rwpb:field-string-max 256;
                rwpb:field-inline "true";
                description "test file name";
              }
              leaf test-result-file-name {
                type string;
                rwpb:field-string-max 256;
                rwpb:field-inline "true";
                description "test result file name";
              }
            } // container pktgen-sim         
          } // case pktgen

        } // choice trafsim-proto-type
      } // container trafsim-mode

      container service-statistics {
        //rwpb:msg-flat true;
        config false;
        rwpb:msg-new TrafsimStats;
        
        container counters {
          config false;

          container protocol {
            config false;

            list commands {
              rwpb:msg-new ProtocolCmdCounters;
              //rwpb:msg-flat true;
              config false;
              key "rwappmgr-instance";

              leaf rwappmgr-instance {
                type uint32;
                description "RW.APPMgr instance";
              }

              list command {
                rwpb:field-inline-max yang;
                max-elements 128;
            
                key "name";
            
                leaf name {
                  type string;
                  rwpb:field-string-max 256;
                  description "Command Name";
                }
            
                leaf periodic-sent {
                  description "Number of messages sent in the last second.";
                  type uint64;
                }

                leaf periodic-received {
                  description "Number of messages received in the last second.";
                  type uint64;
                }

                leaf cumulative-sent {
                  description "Number of total messages sent";
                  type uint64;
                }

                leaf cumulative-received {
                  description "Number of total messages received";
                  type uint64;
                }
              }
            }

            list avps {
              rwpb:msg-new ProtocolAvpCounters;
              //rwpb:msg-flat true;
              config false;
              key "rwappmgr-instance";

              leaf rwappmgr-instance {
                type uint32;
                description "RW.APPMgr instance";
              }

              list avp {
                rwpb:field-inline-max yang;
                max-elements 1024;
            
                key "name";
                
                leaf name {
                  type string;
                  rwpb:field-string-max 256;
                  description "AVP Name";
                }
            
                leaf periodic-sent {
                  description "Number of messages sent in the last second.";
                  type uint64;
                  default 0;
                }

                leaf periodic-received {
                  description "Number of messages received in the last second.";
                  type uint64;
                  default 0;
                }

                leaf cumulative-sent {
                  description "Number of total messages sent";
                  type uint64;
                  default 0;
                }

                leaf cumulative-received {
                  description "Number of total messages received";
                  type uint64;
                  default 0;
                }
              }
            }
          }

          list timer {
            rwpb:msg-new TimerCounters;
            //rwpb:msg-flat true;
            key "rwappmgr-instance";

            leaf rwappmgr-instance {
              type uint32;
              description "RW.APPMgr instance";
            }

            
            leaf t_0ms_25ms {
              description "0ms <= n < 25ms";
              type uint64;
              default 0;
            }
            leaf t_25ms_50ms {
              description "25ms <= n < 50ms";
              type uint64;
              default 0;
            }
            leaf t_50ms_75ms {
              description "50ms <= n < 75ms";
              type uint64;
              default 0;
            }
            leaf t_75ms_100ms {
              description "75ms <= n < 100ms";
              type uint64;
              default 0;
            }
            leaf t_100ms_115ms {
              description "100ms <= n < 115ms";
              type uint64;
              default 0;
            }
            leaf t_115ms_120ms {
              description "115ms <= n < 120ms";
              type uint64;
              default 0;
            }
            leaf t_120ms_167ms {
              description "120ms <= n < 167ms";
              type uint64;
              default 0;
            }
            leaf t_167ms_200ms {
              description "167ms <= n < 200ms";
              type uint64;
              default 0;
            }
            leaf t_200ms_300ms {
              description "200ms <= n < 300ms";
              type uint64;
              default 0;
            }
            leaf t_300ms_400ms {
              description "300ms <= n < 400ms";
              type uint64;
              default 0;
            }
            leaf t_400ms_500ms {
              description "400ms <= n < 500ms";
              type uint64;
              default 0;
            }
            leaf t_500ms_600ms {
              description "500ms <= n < 600ms";
              type uint64;
              default 0;
            }
            leaf t_600ms_700ms {
              description "600ms <= n < 700ms";
              type uint64;
              default 0;
            }
            leaf t_700ms_800ms {
              description "700ms <= n < 800ms";
              type uint64;
              default 0;
            }
            leaf t_800ms_900ms {
              description "800ms <= n < 900ms";
              type uint64;
              default 0;
            }
            leaf t_900ms_1000ms {
              description "900ms <= n < 1000ms";
              type uint64;
              default 0;
            }
            leaf t_1000ms_2000ms {
              description "1000ms <= n < 2000ms";
              type uint64;
              default 0;
            }
            leaf t_2000ms_3000ms {
              description "2000ms <= n < 3000ms";
              type uint64;
              default 0;
            }
            leaf t_3000ms_ {
              description "n >= 3000ms";
              type uint64;
              default 0;
            }
          }
        }

        list traffic {
          rwpb:msg-new TrafficCounters;
          //rwpb:msg-flat true;

          config false;

          
          key "rwappmgr-instance";

          leaf rwappmgr-instance {
            type uint32;
            description "RW.APPMgr instance";
          }

          container periodic {
            config false;

            leaf call-rate {
              description "Instantaneous Call rate";
              type uint64;
              default 0;
            }
        
            leaf incoming-calls {
              description "Incoming calls";
              type uint64;
              default 0;
            }

            leaf outgoing-calls {
              description "Outgoing calls";
              type uint64;
              default 0;
            }
      
            leaf rx-msg-per-sec {
              description "Msgs Received per sec";
              type uint64;
              default 0;
            }

            leaf tx-msg-per-sec {
              description "Msgs Sent per sec";
              type uint64;
              default 0;
            }

            leaf unexpected-msg {
              description "Unexpected messages received";
              type uint64;
              default 0;
            }

            leaf current-calls {
              description "Current Active calls";
              type uint64;
              default 0;
            }

            leaf successful-calls {
              description "Successful calls made";
              type uint64;
              default 0;
            }

            leaf failed-calls {
              description "Failed calls";
              type uint64;
              default 0;
            }

            leaf refused-calls {
              description "Refused calls";
              type uint64;
              default 0;
            }

            leaf aborted-calls {
              description "Aborted calls";
              type uint64;
              default 0;
            }

            leaf timedout-calls {
              description "Timedout calls";
              type uint64;
              default 0;
            }

            leaf successful-traffic-calls {
              description "Successfull traffic calls";
              type uint64;
              default 0;
            }

            leaf successful-init-calls {
              description "Successfull init calls";
              type uint64;
              default 0;
            }

            leaf successful-default-calls {
              description "Successfull default calls";
              type uint64;
              default 0;
            }

            leaf successful-abort-calls {
              description "Successfull abort calls";
              type uint64;
              default 0;
            }
          }

          container cumulative {
        
            leaf call-rate {
              description "Instantaneous Call rate";
              type uint64;
              default 0;
            }
        
            leaf incoming-calls {
              description "Incoming calls";
              type uint64;
              default 0;
            }

            leaf outgoing-calls {
              description "Outgoing calls";
              type uint64;
              default 0;
            }
      
            leaf rx-msg-per-sec {
              description "Msgs Received per sec";
              type uint64;
              default 0;
            }

            leaf tx-msg-per-sec {
              description "Msgs Sent per sec";
              type uint64;
              default 0;
            }

            leaf unexpected-msg {
              description "Unexpected messages received";
              type uint64;
              default 0;
            }

            leaf current-calls {
              description "Current Active calls";
              type uint64;
              default 0;
            }

            leaf successful-calls {
              description "Successful calls made";
              type uint64;
              default 0;
            }

            leaf failed-calls {
              description "Failed calls";
              type uint64;
              default 0;
            }

            leaf refused-calls {
              description "Refused calls";
              type uint64;
              default 0;
            }

            leaf aborted-calls {
              description "Aborted calls";
              type uint64;
              default 0;
            }

            leaf timedout-calls {
              description "Timedout calls";
              type uint64;
              default 0;
            }

            leaf successful-traffic-calls {
              description "Successfull traffic calls";
              type uint64;
              default 0;
            }

            leaf successful-init-calls {
              description "Successfull init calls";
              type uint64;
              default 0;
            }

            leaf successful-default-calls {
              description "Successfull default calls";
              type uint64;
              default 0;
            }

            leaf successful-abort-calls {
              description "Successfull abort calls";
              type uint64;
              default 0;
            }
          }
        }
      } // container trafsim-service-statistics
    } // container service
  } // augment /rwbase:colony  
  
  rpc trafsim-start {
    input {      
      container colony {
        rwpb:msg-new StartTraffic;
        rwpb:msg-flat true;
        rwpb:field-inline "true";
        leaf name {
          rwpb:field-inline "true";
          rwpb:field-string-max 64;
          type string;
        }
        container trafsim-service {
          leaf name {
            rwpb:field-inline "true";
            rwpb:field-string-max 64;
            type string;
          }
        }
      }
    } // input
  } // rpc trafsim-start
    
  
  rpc trafsim-stop {
    input {
      container colony {
        rwpb:msg-new StopTraffic;
        rwpb:msg-flat true;
        rwpb:field-inline "true";
        leaf name {
          rwpb:field-inline "true";
          rwpb:field-string-max 64;
          type string;
        }
        container trafsim-service {
          leaf name {
            rwpb:field-inline "true";
            rwpb:field-string-max 64;
            type string;
          }
        }  
      }
    } // input
  } // rpc trafsim-stop

  rpc trafsim-pause {
    input {
      container colony {
        rwpb:msg-new PauseTraffic;
        rwpb:msg-flat true;
        rwpb:field-inline "true";
        leaf name {
          rwpb:field-inline "true";
          rwpb:field-string-max 64;
          type string;
        }
        container trafsim-service {
          leaf name {
            rwpb:field-inline "true";
            rwpb:field-string-max 64;
            type string;
          }
        }  
      }
    } // input
  } // rpc trafsim-pause

  rpc trafsim-resume {
    input {
      container colony {
        rwpb:msg-new ResumeTraffic;
        rwpb:msg-flat true;
        rwpb:field-inline "true";
        leaf name {
          rwpb:field-inline "true";
          rwpb:field-string-max 64;
          type string;
        }
        container trafsim-service {
          leaf name {
            rwpb:field-inline "true";
            rwpb:field-string-max 64;
            type string;
          }
        }  
      }
    } // input
  } // rpc trafsim-resume

  rpc trafsim-adjust {
    input {
      container colony {
        rwpb:msg-new AdjustTraffic;
        rwpb:msg-flat true;
        rwpb:field-inline "true";
        leaf name {
          rwpb:field-inline "true";
          rwpb:field-string-max 64;
          type string;
        }
        container trafsim-service {
          leaf name {
            rwpb:field-inline "true";
            rwpb:field-string-max 64;
            type string;
          }
          leaf call-rate {
            description "Call-Rate";
            type uint32;
          }
        }  
      }
    } // input
  } // rpc trafsim-pause
  
}
