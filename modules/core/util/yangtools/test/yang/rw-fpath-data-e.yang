/*
 * STANDARD_RIFT_IO_COPYRIGHT
 *
 */

module rw-fpath-data-e
{
    namespace "http://riftio.com/ns/riftware-1.0/rw-fpath-data";
    prefix "rw-fpath-data";
    import rw-base-e {
        prefix rwbase;
    }
    import rw-pb-ext {
        prefix "rwpb";
    }
    import rw-yang-types {
        prefix "rwt";
    }
    import rw-fpath-e {
        prefix rwfpath;
    }
    revision 2014-11-21 {
        description
            "Initial revision.";
        reference
            "RIFT Fpath Operational Data";
    }

    augment /rwbase:colony {                
        container controller-info{
            config false;
            leaf lead-fastpath{
                type uint32;
            }
        }
        
        list fastpath-instance{
            config false;
            rwpb:msg-new FastpathState;
            /*Need to fix it by choice on lport-type*/
            key "task-id";
            
            leaf task-id {
                type uint32;
                description "Fastpath Instance-id";
            }
            leaf hashbin-credit{
                type uint32;
            }
            
            container fabric-context{
                uses rwfpath:vrf-info;
            }
            
            container ipfp{
                list memory-stats{
                    rwpb:field-inline "true";
                    rwpb:field-inline-max "yang";
                    max-elements 24;
                    key "name";
                    leaf name{
                        rwpb:field-inline "true";
                        description "mempool name";
                        type string;
                        rwpb:field-string-max 128;
                    }
                    leaf num-allocs{
                        type uint32;
                    }
                    leaf num-frees{
                        type uint32;
                    }
                    leaf num-active-elem{
                        type uint32;
                    }
                }
                
                uses rwfpath:reassembly-stats;
            }

            container debug{
                uses rwfpath:kernel-stats;
                container memory-stats{
                    rwpb:field-inline "true";
                    rwpb:msg-new MempoolStats;
                    rwpb:msg-flat true;
                    list mempool-name{
                        rwpb:field-inline-max "yang";
                        max-elements 24;
                        key "name";
                        leaf name{
                            description "mempool name";
                            type string;
                            rwpb:field-string-max 128;
                        }
                        leaf ring{
                            description "mempool ring name";
                            type string;
                            rwpb:field-string-max 128;
                        }
                        leaf size{
                            description "size";
                            type uint32;
                        }
                        leaf header-size{
                            description "header-size";
                            type uint32;
                        }
                        leaf element-size{
                            description "element size";
                            type uint32;
                        }
                        leaf trailer-size{
                            description "trailer size";
                            type uint32;
                        }
                        leaf total-object-size{
                            description "total object size";
                            type uint32;
                        }
                        leaf private-data-size{
                            description "private data size";
                            type uint32;
                        }
                        leaf physical-address{
                            type uint64;
                            description "physical address";
                        }
                        leaf page-num{
                            type uint32;
                            description "page number";
                        }
                        leaf page-shift{
                            type uint32;
                            description "page shift";
                        }
                        leaf page-mask{
                            type uint32;
                            description "page mask";
                        }
                        leaf element-va-start{
                            description "element virtual address start";
                            type uint64;
                        }
                        leaf element-va-end{
                            description "element virtual address end";
                            type uint64;
                        }
                        list lcore-cache{
                            rwpb:field-inline-max "yang";
                            max-elements 64;//RTE_MAX_LCORE
                            key "id";
                            leaf id{
                                description "lcore id";
                                type uint32;
                            }
                            leaf length{
                                description "number of mbufs in cache available in the cache";
                                type uint32;
                            }
                        }
                    }
                }
            }
        }
        container scriptable-lb {
            config false;
            rwpb:msg-new ScriptableLBInfo;

            list fastpath {
                rwpb:field-inline-max yang;
                //rwpb:msg-new Fastpath;

                rwpb:msg-flat true;
                max-elements 1;
                key "instance";

                leaf instance {
                    type uint32;
                    description "FPATH instance number";
                }


                list service {
                    rwpb:field-inline-max yang;
                    max-elements 1;
                    key "service-name";
                    
                    leaf service-name {
                        type string;
                        rwpb:field-string-max 64;
                        rwpb:field-inline "true";
                        description "service name";
                    }
                    container statistics {
                        leaf active-fwd-session {
                            type uint32;
                            description "active fwd sessions";
                        }
                        leaf active-rev-session {
                            type uint32;
                            description "active rev sessions";
                        }
                        leaf clnt-fwd-pkt-rcvd {
                            type uint64;
                            description "packets received in the fwd direction";
                        }
                        leaf srvr-fwd-pkt-sent {
                            type uint64;
                            description "packets sent to the server";
                        }
                        leaf srvr-rev-pkt-rcvd {
                            type uint64;
                            description "packets received from server";
                        }
                        leaf clnt-rev-pkt-sent {
                            type uint64;
                            description "packets sent to clients";
                        }
                        leaf clnt-fwd-byte-rcvd {
                            type uint64;
                            description "bytes received in the fwd direction";
                        }
                        leaf srvr-fwd-byte-sent {
                            type uint64;
                            description "bytes sent to the server";
                        }
                        leaf srvr-rev-byte-rcvd {
                            type uint64;
                            description "bytes received from server";
                        }
                        leaf clnt-rev-byte-sent {
                            type uint64;
                            description "bytes sent to clients";
                        }                     
                        leaf fwd-pkt-drop {
                            type uint64;
                            description "packets sent to clients";
                        }
                        leaf fwd-pkt-drop-no-session {
                            type uint64;
                            description "packets sent to clients";
                        }
                        leaf fwd-pkt-drop-max-session {
                            type uint64;
                            description "packets sent to clients";
                        }
                        leaf rev-pkt-drop {
                            type uint64;
                            description "packets sent to clients";
                        }
                        leaf rev-pkt-drop-no-session {
                            type uint64;
                            description "packets sent to clients";
                        }
                        leaf clnt-fwd-rate-pps {
                            type uint32;
                            description "packets rate received in the fwd direction";
                        }
                        leaf srvr-fwd-rate-pps {
                            type uint32;
                            description "packets rate sent to the server";
                        }
                        leaf srvr-rev-rate-pps {
                            type uint32;
                            description "packets rate received from server";
                        }
                        leaf clnt-rev-rate-pps {
                            type uint32;
                            description "packets rate sent to clients";
                        }
                        leaf clnt-fwd-rate-mbps {
                            type uint32;
                            description "packets rate received in the fwd direction";
                        }
                        leaf srvr-fwd-rate-mbps {
                            type uint32;
                            description "packets rate sent to the server";
                        }
                        leaf srvr-rev-rate-mbps {
                            type uint32;
                            description "packets rate received from server";
                        }
                        leaf clnt-rev-rate-mbps {
                            type uint32;
                            description "packets rate sent to clients";
                        }
                    }
                    
                    list fwd-sessions {
                        rwpb:field-inline-max yang;
                        max-elements 32;
                        key "sessionid";
                        
                        leaf sessionid {
                            type uint32;
                        }
                        uses rwfpath:slb-session-info;
                    }
                    
                    list rev-sessions {
                        rwpb:field-inline-max yang;
                        max-elements 32;
                        key "sessionid";
                        
                        leaf sessionid {
                            type uint32;
                        }
                        uses rwfpath:slb-session-info;
                    }
                    
                    list bindings {
                        rwpb:field-inline-max yang;
                        max-elements 32;
                        key "bindingid";
                        
                        leaf bindingid {
                            type uint32;
                        }
                        container server-info {
                            leaf server-group {
                                type string;
                                rwpb:field-string-max 64;
                                description "service group";
                            }
                            leaf server-address {
                                type rwt:ip-address;
                                rwpb:field-string-max 46;
                            }
                        }
                        container fwd-session {
                            uses rwfpath:slb-session-info;
                        }
                        container rev-session {
                            uses rwfpath:slb-session-info;
                        }
                    }
                    
// Augmented proto-specific stats goes here
                    container  proto-specific-stat {
                        choice lb-protocol-type {
                            case lb-dns {
                                container dns-lb-stat {
                                    list qname-stat {
                                        rwpb:field-inline-max yang;
                                        max-elements 32;
                                        key "query-name";
                                        leaf query-name {
                                            type string;
                                            rwpb:field-string-max 32;
                                            description "qname";
                                        }
                                        leaf occurance {
                                            type uint32;
                                        }
                                    }
                                }
                            }
                            case lb-radius {
                                container radius-lb-stat {
                                    list username-stat {
                                        rwpb:field-inline-max yang;
                                        max-elements 32;
                                        key "domain-name";
                                        leaf domain-name {
                                            type string;
                                            rwpb:field-string-max 32;
                                            description "domain";
                                        }
                                        leaf occurance {
                                            type uint32;
                                        }
                                    }
                                }
                            }
                        }
                    }
                }
            }
            
            list service {
                rwpb:field-inline-max yang;
                max-elements 1;
                key "service-name";
                
                leaf service-name {
                    type string;
                    rwpb:field-string-max 64;
                    rwpb:field-inline "true";
                    description "service name";
                }
                container plugin-script {
                    leaf code {
                        type string;
                        description "scripting code";
                    }
                }
            }
        }
        container virtual-fabric {
            config false;
            rwpb:msg-new VirtualFabricInfo;
            rwpb:msg-flat true;
            rwpb:msg-proto-max-size "5700000";
            list fastpath{
                rwpb:field-inline-max yang;
                rwpb:msg-proto-max-size "5700000";
                max-elements 1;
            
                key "instance";
            
                leaf instance {
                    type uint32;
                    description "FPATH instance number";
                }
                container statistics {
                    leaf vf-pkt-rcvd {
                        type uint64;
                    }
                    leaf vf-pkt-rcv-dropped {
                        type uint64;
                    }
                    leaf vf-pkt-rcv-port-tx {
                        type uint64;
                    }
                    leaf vf-pkt-rcv-policy-fwd {
                        type uint64;
                    }
                    leaf vf-pkt-rcv-in-lookup {
                        type uint64;
                    }
                    leaf vf-pkt-rcv-dlvr-app {
                        type uint64;
                    }
                    leaf vf-pkt-rcv-dlvr-kern {
                        type uint64;
                    }
                    leaf vf-pkt-rcv-ip-reasm {
                        type uint64;
                    }
                    leaf vf-pkt-rcv-echo {
                        type uint64;
                    }
                    leaf vf-pkt-xmit {
                        type uint64;
                    }
                    leaf vf-pkt-tx-dropped {
                        type uint64;
                    }
                    leaf vf-pkt-tx-port-tx {
                        type uint64;
                    }
                    leaf vf-pkt-tx-policy-fwd {
                        type uint64;
                    }
                    leaf vf-pkt-tx-in-lookup {
                        type uint64;
                    }
                    leaf vf-pkt-tx-dlvr-app {
                        type uint64;
                    }
                    leaf vf-pkt-tx-dlvr-kern {
                        type uint64;
                    }
                    leaf vf-pkt-tx-ip-reasm {
                        type uint64;
                    }
                    leaf vf-pkt-tx-echo {
                        type uint64;
                    }
                }
                list vfap {
                    rwpb:field-inline-max yang;
                    max-elements 128;
                    
                    key "vfapid";
                    
                    leaf vfapid {
                        type uint32;
                        description "Virtual-Fabric Port Identifier";
                    }
                    leaf groupid {
                        type uint32;
                        description "Virtual-Fabric Port Identifier";
                    }
                    leaf local-vfap {
                        type rwfpath:yes-no;
                        description "This is my local VFAP";
                    }
                    list ip{
                        rwpb:field-inline-max yang;
                        max-elements 16;
                    
                        key "address";
                    
                        leaf address {
                            type rwt:ip-address;
                            rwpb:field-string-max 46;
                            description "IP addess bound to the VFAP";
                        }
                        leaf echo-request-sent {
                            type uint64;
                            description "Number of VF-Echo Request packet sent to this VFAP";
                        }
                        leaf echo-response-rcvd {
                            type uint64;
                            description "Number of VF-Echo Response Packet received from this VFAP";
                        }
                        leaf echo-request-rcvd {
                            type uint64;
                            description "Number of VF-Echo Request Packet received from this VFAP";
                        }
                        leaf echo-response-sent {
                            type uint64;
                            description "Number of VF-Echo Response Packet sent to this VFAP";
                        }
                        leaf average-transit-latency {
                            type uint64;
                            description "Average transit latency from this VFAP";
                        }
                    }
                }
                list vsap {
                    rwpb:field-inline-max yang;
                    max-elements 128;
                
                    key "vsapid";
                
                    leaf vsapid {
                        type uint32;
                        description "Virtual Service Access Point Identifier";
                    }
                    leaf groupid {
                        type uint32;
                        description "Virtual Service Access Point Identifier";
                    }
                
                    list vfap {
                        rwpb:field-inline-max yang;
                        max-elements 32;
                    
                        key "vfapid";
                    
                        leaf vfapid {
                            type uint32;
                            description "Virtual-Fabric Port Identifier";
                        }
                        list ip {
                            rwpb:field-inline-max yang;
                            max-elements 16;
                        
                            key "address";
                        
                            leaf address {
                                type rwt:ip-address;
                                rwpb:field-string-max 46;
                                description "IP addess bound to the VFAP";
                            }
                        }
                    }
                
                    leaf local-vsap {
                        type rwfpath:yes-no;
                        description "This is my local VSAP";
                    }
                
                    leaf pkts-rcvd {
                        type uint64;
                        description "Number of Packet received for this VSAP";
                    }
                    leaf pkts-sent {
                        type uint64;
                        description "Number of Packets sent for this VSAP";
                    }
                }
            }
        }



        container external-app-plugin {
            config false;
            rwpb:msg-new ExtPpPlugin;
            rwpb:msg-flat true;
            rwpb:msg-proto-max-size "3600000";
            list fastpath {
                rwpb:field-inline-max yang;
                max-elements 1;

                key "instance";

                leaf instance {
                    type uint32;
                    description "FPATH instance number";
                }

                container statistics {
                    leaf num-flow-cfg {
                        type uint32;
                    }
                    leaf num-server-lb {
                        type uint32;
                    }
                    leaf num-client {
                        type uint32;
                    }
                    leaf num-lb-vsapid {
                        type uint32;
                    }
                    leaf lb-sent-to-vsap {
                        type uint64;
                    }
                    leaf lb-drop-no-vsap-for-slice {
                        type uint64;
                    }
                    leaf srv-lb-drop-no-vsap {
                        type uint64;
                    }
                    leaf srv-rnat-drop-no-binding {
                        type uint64;
                    }
                }

                list clients {
                    rwpb:field-inline-max yang;
                    max-elements 64;
             
                    key "index";

                    leaf index {
                        type uint32;
                    }
                    leaf ncid {
                        type uint32;
                    }
                    leaf ip-address {
                        type rwt:ip-address;                                                
                        rwpb:field-string-max 46;
                    }
                    leaf port {
                        type uint16;
                    }

                    leaf protocol {
                        type enumeration {
                            enum udp { value 0; }
                            enum tcp  { value 1; }
                        }
                    }
                    leaf vsapid {
                        type uint32;
                    }
                    leaf reverse-fwd {
                        type uint64;
                    }
                }

                list servers {
                    rwpb:field-inline-max yang;
                    max-elements 64;

                    key "index";

                    leaf index {
                        type uint32;
                    }
                    leaf ncid {
                        type uint32;
                    }
                    leaf ip-address {
                        type rwt:ip-address;
                        rwpb:field-string-max 46;
                    }
                    leaf port {
                        type uint16;
                    }

                    leaf protocol {
                        type enumeration {
                            enum udp { value 0; }
                            enum tcp  { value 1; }
                        }
                    }
                    leaf vsapid {
                        type uint32;
                    }
                    leaf nat-ip-address {
                        type rwt:ip-address;
                        rwpb:field-string-max 46;
                    }
                    leaf num-bindings {
                        type uint32;
                    }
                    leaf forward-nat-fwd {
                        type uint64;
                    }
                    leaf reverse-nat-fwd {
                        type uint64;
                    }
                }
            }
        }
        container load-balancer {
            config false;
            rwpb:msg-new LoadbalancerInfo;
            rwpb:msg-flat true;
            list fastpath{
                rwpb:field-inline-max yang;
                max-elements 1;
            
                key "instance";
            
                leaf instance {
                    type uint32;
                    description "Virtual-Fabric Port Identifier";
                }
                list worker {
                    rwpb:field-inline-max yang;
                    max-elements 32;
                
                    key "id";
                
                    leaf id {
                        type uint32;
                        description "Load Balancer worker id";
                    }
                    leaf fwd-bindings {
                        type uint32;
                        description "number of current forward direction bindings";
                    }
                    leaf rev-bindings {
                        type uint32;
                        description "number of current reverse direction bindings";
                    }
                    leaf fwd-pkt-received {
                        type uint64;
                        description "total number of forward direction packets received";
                    }
                    leaf fwd-pkt-xmit {
                        type uint64;
                        description "total number of forward direction packets transmitted";
                    }
                    leaf fwd-pkt-drop {
                        type uint64;
                        description "total number of forward direction packets dropped";
                    }
                    leaf rev-pkt-received {
                        type uint64;
                        description "total number of reverse direction packets received";
                    }
                    leaf rev-pkt-xmit {
                        type uint64;
                        description "total number of reverse direction packets transmitted";
                    }
                    leaf rev-pkt-drop {
                        type uint64;
                        description "total number of reverse direction packets dropped";
                    }
                }
            }
        }
        container distributed-classifier {
            config false;
            rwpb:msg-new ClassifierInfo;
            rwpb:msg-flat true;

            list fastpath{
                rwpb:field-inline-max yang;
                max-elements 1;
                key "instance";
        
                leaf instance {
                    type uint32;
                    description "FPATH instance number";
                }
                list service {
                    rwpb:field-inline-max yang;
                    max-elements 1;
                    key "service-id";
                    leaf service-id {
                        type uint32;
                        description "Classifier Service Id";
                    }

                    leaf user-application {
                        type string;
                        rwpb:field-string-max 64;
                        rwpb:field-inline "true";
                        description "User Application using the classifier service";
                    }

                    leaf user-application-id {
                        type uint32;
                        description "Application ID for the user application using the classifier service";
                    }
          
                    leaf distribution-group-size {
                        type uint32;
                        description "Size of vsapid group for session distribution";
                    }

                    leaf distribution-score-levels {
                        type uint32;
                        description "Number of score levels for VSAPID weights";
                    }

                    list score-list {
                        max-elements 11;
                        key "score-level";

                        leaf score-level {
                            type uint32;
                            description "VSAPID Weight Score level";
                        }
                        leaf score-count {
                            type uint32;
                            description "VSAPID Weight Score level count";
                        }
                    }
          
                    list vsapid-list {
                        max-elements 1024;
                        key "vsapid";
        
                        leaf vsapid {
                            type uint32;
                            description "VSAPID";
                        }
        
                        leaf weight {
                            type uint32;
                            description "Weight associated with VSAPID";
                        }

                        leaf score-level {
                            type uint32;
                            description "Score level associated with VSAPID";
                        }
                        container stats {
                            leaf pkt-new-session {
                                type uint64;
                                description "New sessions forwarded to VSAPID";
                            }
                            leaf pkt-cache-hit {
                                type uint64;
                                description "Packets forwarded due to cache hit";
                            }
                        }
                    }

                    list classifier-work {
                        max-elements 8;
                        key "worker-id";

                        leaf worker-id {
                            type uint32;
                            description "Classifier worker Id";
                        }
                        container stats {
                            leaf pkt-rcvd {
                                type uint64;
                                description "Total packets received in this worker instance";
                            }
                            leaf pkt-processed {
                                type uint64;
                                description "Total packets processed in this worker instance";
                            }
                            leaf pkt-cache-hit {
                                type uint64;
                                description "Total packets finding binding entry session binding cache";
                            }
                            leaf pkt-enqueue-fail {
                                type uint64;
                                description "Total packets failed to get enqueued for further processing";
                            }
                            leaf pkt-new-session {
                                type uint64;
                                description "Total packets identified as new sessions";
                            }
                            leaf pkt-delivery-failure {
                                type uint64;
                                description "Total packets failed to get delivered";  
                            }
                        }
                    }
                }
            }
        }


        container ip-classifier {
            config false;
            rwpb:msg-new IpClassifierInfo;
            rwpb:msg-flat true;
            rwpb:msg-proto-max-size "1700000";
            list fastpath {
                rwpb:field-inline-max yang;
                rwpb:msg-proto-max-size "501724";
                max-elements 1;
            
                key "instance";
            
                leaf instance {
                    type uint32;
                    description "FPATH instance number";
                }

                container statistics {
                    leaf num_signatures {
                        type uint32;
                    }
                    leaf num_local_hashbins {
                        type uint32;
                    }
                    leaf num_local_flows {
                        type uint32;
                    }
                    leaf num_remote_flows {
                        type uint32;
                    }
                    leaf num_hbin_flows {
                        type uint32;
                    }
                    leaf num_flow_cache {
                        type uint32;
                    }
                    leaf signature_add {
                        type uint64;
                    }
                    leaf signature_delete {
                        type uint64;
                    }
                    leaf signature_add_fail {
                        type uint64;
                    }
                    leaf signature_match {
                        type uint64;
                    }
                    leaf signature_app_dlvr {
                        type uint64;
                    }
                    leaf flow_add {
                        type uint64;
                    }
                    leaf flow_delete {
                        type uint64;
                    }
                    leaf flow_add_lbin {
                        type uint64;
                    }
                    leaf flow_add_rbin_fwd {
                        type uint64;
                    }
                    leaf flow_add_rbin_rcvd {
                        type uint64;
                    }
                    leaf flow_add_fail {
                        type uint64;
                    }
                    leaf flow_add_fail_bounce {
                        type uint64;
                    }
                    leaf flow_add_fail_dupl {
                        type uint64;
                    }
                    leaf flow_add_fail_no_rhbin {
                        type uint64;
                    }
                    leaf flow_add_fail_no_lhbin {
                        type uint64;
                    }
                    leaf flow_add_fail_validation {
                        type uint64;
                    }
                    leaf flow_delete_lbin {
                        type uint64;
                    }
                    leaf flow_delete_rbin_fwd {
                        type uint64;
                    }
                    leaf flow_delete_rbin_rcvd {
                        type uint64;
                    }
                    leaf flow_delete_fail {
                        type uint64;
                    }
                    leaf flow_lookup {
                        type uint64;
                    }
                    leaf flow_lookup_lbin {
                        type uint64;
                    }
                    leaf flow_lookup_rbin_fwd {
                        type uint64;
                    }
                    leaf flow_lookup_rbin_rcvd {
                        type uint64;
                    }
                    leaf flow_lookup_success {
                        type uint64;
                    }
                    leaf flow_lookup_rbin_nosig {
                        type uint64;
                    }
                    leaf flow_cache_add_req {
                        type uint64;
                    }
                    leaf flow_cache_del_req {
                        type uint64;
                    }
                    leaf flow_cache_add {
                        type uint64;
                    }
                    leaf flow_cache_add_fail {
                        type uint64;
                    }
                    leaf flow_cache_delete {
                        type uint64;
                    }
                    leaf flow_cache_delete_fail {
                        type uint64;
                    }
                    leaf flow_cache_purge {
                        type uint64;
                    }
                    leaf flow_cache_lookup {
                        type uint64;
                    }
                    leaf flow_cache_lookup_succ {
                        type uint64;
                    }
                }

                list signatures {                                                                                                          
                    rwpb:field-inline-max yang;
                    max-elements 32;
            
                    key "signature-id";
            
                    leaf signature-id {
                        type uint32;
                        description "Signature ID";
                    }
                    leaf priority {
                        type uint32;
                    }
                    leaf flow-type {
                        type uint32;
                    }
                    leaf ncid {
                        type uint32;
                    }
                    leaf ip-address {
                        type rwt:ip-address;                                                
                        rwpb:field-string-max 46;
                    }
                    leaf app_id {
                        type uint32;
                    }
                    leaf appdata {
                        type uint32;
                    }
                    leaf length {
                        type uint32;
                    }
                    leaf key-val {
                        type string; 
                        rwpb:field-string-max 128;
                    }
                    leaf key-mask {
                        type string;
                        rwpb:field-string-max 128;
                    }
                    leaf nh-id {
                        description "Nexthop Handle ID";
                        type uint32;
                    }
                    leaf nh-nc-id {
                        description "Nexthop Handle context-id";
                        type uint32;
                    }
                }

                container locally-owned {
                    uses rwfpath:ip-flows-list;
                }
                container remote-installed {
                    uses rwfpath:ip-flows-list;
                }
                container cache {
                    uses rwfpath:ip-flows-list;
                }
                container hashbin {
                    uses rwfpath:ip-flows-list;
                }

                list hbin-distribution {
                    rwpb:field-inline-max yang;
                    max-elements 1024;

                    key "id";

                    leaf id {
                        type uint32;
                        description "id";
                    }
                    leaf location {
                        type enumeration {                                                                         
                            enum unknown  { value 0; }
                            enum local   { value 1; }
                            enum remote  { value 2; }
                        }
                    }
                    leaf fpath-inst {
                        type uint32;
                    }
                    leaf vsap-id {
                        type uint32;
                    }
                }
            }
        }

        container fast-flow {
          config false;
          rwpb:msg-new FastFlowInfo;
          rwpb:msg-flat true;
          rwpb:msg-proto-max-size "413816";

          list fastpath{
            rwpb:field-inline-max yang;
            rwpb:msg-proto-max-size "413776";
            max-elements 1;
            key "instance";
        
            leaf instance {
              type uint32;
              description "FPATH instance number";
            }

            leaf flow-tx-enqueue-failure {
              type uint64;
              description "Number of flow requests failed to get enqueued for transmission";
            }

            leaf flow-tx-mem-alloc-failure {
              type uint64;
              description "Number of flow requests failed to get get memory buffer for transmission";
            }

            
            leaf flow-rx-enqueue-failure {
              type uint64;
              description "Number of flow requests failed to get enqueued for reception";
            }
            list peer-fpath-list {
              max-elements 1024;
              key "fpath-id";

              leaf fpath-id {
                type uint32;
                description "Fpath instance";
              }
              
              leaf vsapid {
                type uint32;
                description "VSAPID";
              }

              leaf flow-add-req-tx-initial {
                type uint64;
                description "Number of initial flow-add request messages sent";
              }
              
              leaf flow-add-req-tx-retry {
                type uint64;
                description "Number of retried flow-add request messages";
              }
              
              leaf flow-add-req-tx-failed {
                type uint64;
                description "Number of flow-add request messages failed";
              }
              
              leaf flow-add-rsp-tx-initial {
                type uint64;
                description "Number of initial flow-add response messages sent";
              }

              leaf flow-add-rsp-tx-retry {
                type uint64;
                description "Number of retried flow-add response messages sent";
              }

              leaf flow-del-req-tx-initial {
                type uint64;
                description "Number of initial flow-delete request messages sent";
              }

              leaf flow-del-req-tx-retry {
                type uint64;
                description "Number of retried flow-delete request messages";
              }

              leaf flow-del-req-tx-failed {
                type uint64;
                description "Number of flow-delete request messages failed";
              }

              leaf flow-del-rsp-tx-initial {
                type uint64;
                description "Number of initial flow-delete response messages sent";
              }

              leaf flow-del-rsp-tx-retry {
                type uint64;
                description "Number of retried flow-delete response messages sent";
              }
              
              leaf flow-add-req-rx-initial {
                type uint64;
                description "Number of initial flow-add request messages received";
              }

              leaf flow-add-req-rx-retry {
                type uint64;
                description "Number of retried flow-add request messages received";
              }

              leaf flow-add-rsp-rx-initial {
                type uint64;
                description "Number of initial flow-add response messages received";
              }

              leaf flow-add-rsp-rx-retry {
                type uint64;
                description "Number of retried flow-add response messages received";
              }

              leaf flow-del-req-rx-initial {
                type uint64;
                description "Number of initial flow-delete request messages received";
              }

              leaf flow-del-req-rx-retry {
                type uint64;
                description "Number of retried flow-delete request messages received";
              }

              leaf flow-del-rsp-rx-initial {
                type uint64;
                description "Number of initial flow-delete response messages received";
              }

              leaf flow-del-rsp-rx-retry {
                type uint64;
                description "Number of retried flow-delete response messages received";
              }

              leaf rsp-tmr-skew-detected {
                type uint64;
                description "Number of responses with transaction-start timestamp greater than transaction-end timestamp";
              }
              
              leaf response-less-5ms {
                type uint64;
                description "Number of responses with RTT less than 5ms";
              }
              
              leaf response-5ms-10ms {
                type uint64;
                description "Number of responses with RTT between 5ms to 10ms";
              }

              leaf response-10ms-25ms {
                type uint64;
                description "Number of responses with RTT between 10ms to 25ms";
              }

              leaf response-25ms-50ms {
                type uint64;
                description "Number of responses with RTT between 25ms to 50ms";
              }

              leaf response-50ms-100ms {
                type uint64;
                description "Number of responses with RTT between 50ms to 100ms";
              }
               
              leaf response-100ms-250ms {
                type uint64;
                description "Number of responses with RTT between 100ms to 250ms";
              }

              leaf response-250ms-500ms {
                type uint64;
                description "Number of responses with RTT between 250ms to 500ms";
              }

              leaf response-more-500ms {
                type uint64;
                description "Number of responses with RTT more than 500ms";
              }
              leaf incoming-queue-size {
                type uint64;
                description "Size of message queue for request received from peer and pending de-allocation";
              }
              leaf outgoing-queue-size {
                type uint64;
                description "Size of message queue for request sent to peer and waiting response";
              }
              
              leaf slow-retrans-queue-size {
                type uint64;
                description "Size of message slow retransmit queue for request sent to peer and waiting response";
              }
            }
          }
          
        } // Container fast-flow
    }
}
