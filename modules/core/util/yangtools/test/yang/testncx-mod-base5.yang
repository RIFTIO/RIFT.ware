/* STANDARD_RIFT_IO_COPYRIGHT */

/**
 * @file testncx-mod-base5.yang
 * @author Tom Seidenberg
 * @date 2014/03/25
 * @brief yangncx test file for modules
 */

module testncx-mod-base5
{
  namespace "http://riftio.com/ns/core/util/yangtools/tests/testncx-mod-base5";
  prefix "tnmb5";

  import testncx-mod-base4 { prefix "tnmb4-b5"; }

  description "Module testing for yangncx.";
  revision 2014-03-25 { description "Initial version"; }

  typedef b5t1 {
    type tnmb4-b5:b4t1;
    description "A typedef of b4t1 from base4, in base5";
  }
}
