/*
 * STANDARD_RIFT_IO_COPYRIGHT
 *
 */

module rwpaas-environments-d {
  namespace "http://riftio.com/ns/riftware-1.0/rwpaas-environments";
  prefix "rwenv";

  import rw-pb-ext { prefix "rwpb"; }
  import rw-yang-types { prefix rwt; }
  import ietf-inet-types { prefix "inet"; }
  import ietf-yang-types { prefix "yang"; }
  import rwiaas-workspaces-d { prefix "rwworkspaces"; }

  revision 2015-01-28 {
    description
      "Initial revision. This YANG file captures the
      data model for provisioning PaaS layer environments.";     
    reference       
      "Derived from earlier versions of base YANG files";
  } 
    
  list environments {
    description "List of environments in the cloud.";
    key name;
    leaf name {
      description "Name of the environment.";
      type string;
    }
    uses rwworkspaces:quotas;
  }
}
