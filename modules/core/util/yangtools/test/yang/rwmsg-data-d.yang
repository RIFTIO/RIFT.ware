/* STANDARD_RIFT_IO_COPYRIGHT */
/**
 * @file rwmsg-data-d.yang
 * @author Grant Taylor
 * @date 2014/8/1
 * @brief RiftWare Yang data schema for the RW.Msg
 */

module rwmsg-data-d
{
  namespace "http://riftio.com/ns/riftware-1.0/rwmsg-data";
  prefix "rwmsg";

  import rw-base-d {
    prefix rwbase;
  }

  import rw-pb-ext {
    prefix "rwpb";
  }

  import rw-yang-types {
    prefix "rwt";
  }

  description "RW.Msg data definitions";

  revision 2014-08-01 {
    description "Initial revision";
    reference "None";
  }

  typedef rwmsg_payload_yenum {
    type enumeration {
      enum RAW;  
      enum PBAPI;
      enum TEXT;
      enum MSGCTL;
    }
  }

  typedef rwmsg_methb_yenum {
    type enumeration { 
      enum SRVCHAN;
      enum BROSRVCHAN;
    }
  }

  typedef rwmsg_channel_yenum {
    type enumeration { 
      enum NULL;
      enum CLI;
      enum SRV;
      enum BROCLI;
      enum BROSRV;
      //?? peer
    }
  }

  typedef rwmsg_skstate_yenum {
    type enumeration { 
      enum NNSK_IDLE;
      enum NNSK_CONNECTED;
    }
  }

  grouping sockets {
    list sockets {
      rwpb:msg-new Chansocket;
      description "Detail around a channel socket";

      leaf pri {
        type uint8;
      }
      leaf paused {
        type boolean;
      }
      leaf connected {
        type boolean;
      }
      leaf state {
        type rwmsg_skstate_yenum;
      }
    }
  }

  grouping methbindings {
    list methbindings {
      rwpb:msg-new Methbinding;
      description "Detail around a method to channel binding";

      leaf btype {
	type rwmsg_methb_yenum;
      }
      leaf path {
	rwpb:field-inline true;
	rwpb:field-string-max 512;
	type string;
      }
      leaf pathhash {
	type uint64;
      }
      leaf payfmt {
	type rwmsg_payload_yenum;
      }
      leaf pbapi_srvno {
	type uint32;
      }
      leaf pbapi_methno {
	type uint32;
      }
      leaf methno {
	type uint32;
      }
      leaf srvchanct {
	description "Total number of srvchan(s) bound to this path/payfmt/methno";
	type uint32;
      }
    }
  }

  grouping channel_info {
    list channels {
      rwpb:msg-new Channelinfo;
      leaf type {
	description "Channel Type";
	type rwmsg_channel_yenum;
      }
      leaf clict {
        description "Number of clients";  // should be number of active or recent clients
        type uint32;	
      }
      leaf id {
	description "Channel ID";
	type uint64;
      }

      leaf peer_id {
	description "Peer ID";
	type uint64;
      }
      leaf peer_pid {
	description "Peer PID";
	type uint64;
      }
      leaf peer_ip {
	description "Peer IP";
	type rwt:ip-address;
	rwpb:field-string-max 46;
	rwpb:field-inline true;
      }

      // [bro]srvchan method table
      uses methbindings;

      // channel socket detail
      uses sockets;

      // brosrvchan clistream table for the channel?

      // reqs in channel's various queues / hashes...

      // stats...
    }
  }

  grouping rwbroker_info {
    list brokers {
      rwpb:msg-new Brokerinfo;
      description "Broker Status";

      leaf "instance_uri" {
	description "";
	type string;
      }

      uses channel_info;
    }
  }

  // show messaging ( info | ... )
  augment /rwbase:messaging {
    container rwmsg {
      rwpb:msg-new Rwmsg;
      rwpb:field-inline true;
      config false;

      uses rwbroker_info;
    }
  }


} // module rwmsg-data-d
