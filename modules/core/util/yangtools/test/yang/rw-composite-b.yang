/* STANDARD_RIFT_IO_COPYRIGHT */

/**
 * @file rw-composite.yang
 * @author Vinod Kamalaraj
 * @date 2014/10/1
 * @brief A compsite YANG file that imports all other modules loaded by
 * rwuagent. This YANG file gives the uagent a global schema view
 */

module rw-composite-b
{
  namespace "http://riftio.com/ns/riftware-1.0/rw-composite";
  prefix "rwcomp";

  import rw-base-b
  {
    prefix "rw-base";
  }
  import rw-fpath-b
  {
    prefix "rw-fpath";
  }

  import rwuagent-cli-b
  {
     prefix "rwua";     
  }

  import rw-appmgr-b
  {
    prefix "rwappmgr";
  }
}
