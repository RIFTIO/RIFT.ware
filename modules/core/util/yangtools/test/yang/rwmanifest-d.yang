/*
 * STANDARD_RIFT_IO_COPYRIGHT
 *
 */

module rwmanifest-d
{
  namespace "http://riftio.com/ns/riftware-1.0/rwmanifest";
  prefix "rwmanifest";

  import rw-pb-ext { prefix "rwpb"; }
  import rw-yang-types { prefix "rwt"; }

  description
    "RW.Manifest definition.
    A RiftWare manifest is used to bootstrap a running instance of RiftWare.";

  revision 2014-03-12 {
    description
      "Initial implementation of RW.Manifest.";
    reference
      "RW.VX Software Component Document";
  }

  typedef rwcal-cloud-type {
    type enumeration {
      // This type is only to be used for unit testing.  It is a mock driver
      // that does not actually communicate with anything over the network,
      // rwther, it has a number of prebaked properties that are used to verify
      // the rwcal_cloud APIs during unit testing.
      enum MOCK;
      enum EC2_US_EAST;
      enum OPENSTACK_AUTH_URL;
      enum VSPHERE;
    }
  }

  grouping rwvcs-variable-list {
    leaf-list python-variable {
      description "List of Python variable assignments";
      type string;
    }
  }

  grouping action-list {
    list action {
      description "This section contains a sequence of RW.VCS actions";
      key "name";
      rwpb:msg-new VcsAction;

      leaf name {
        description "Name of the action within the sequence";
        type string;
      }

      grouping rwvcs-python-loop {
        leaf python-loop-expression {
          description "Python expression";
          type string;
        }

        leaf python-loop-iterate {
          description "Python iteration";
          type string;
        }
      }
      uses rwvcs-python-loop;

      choice action {
        case annex {
          container annex {
            leaf component-name {
              description "Name of the component type in the inventory";
              type leafref {
                path "../../../../../../../component/component-name";
              }
            }
            leaf instance-id {
              description "ID of the component instance in the inventory";
              type string;
            }
            leaf instance-name {
              description "Name of the component instance in the inventory";
              type string;
            }
          }
        }

        case start {
          container start {
            rwpb:msg-new ActionStart;

            uses rwvcs-variable-list;
            leaf component-name {
              description "Name of the component type in the inventory";
              type leafref {
                path "../../../../../../../component/component-name";
              }
            }
            leaf instance-id {
              description "ID of the component instance in the inventory";
              type string;
            }
            leaf instance-name {
              description "Name of the component instance in the inventory";
              type string;
            }
          }
        }

        case sleep {
          container sleep {
            leaf wait-time-usec {
              description "Time to wait while sleeping";
              type uint32;
            }
          }
        }
      } // choice action
    } // list action
  } // grouping action-list

  grouping rwvcs-event-list {
    container event-list {
      description "";
      rwpb:msg-new VcsEventList;

      list event {
        description "This section contains a list of RW.VCS events";
        key "name";
        rwpb:msg-new VcsEvent;

        leaf name {
          description "Name of the event";
          type string;
        }

        uses action-list;
      } // list event
    } // container event-list
  } // grouping rwvcs-event-list

  grouping rwvcs-rwcolony {
    container rwcolony {
      description "This section defines a RW.VCS rwcolony component";
      rwpb:msg-new VcsRwColony;

      uses rwvcs-event-list;
    }
  }

  grouping rwvcs-rwcluster {
    container rwcluster {
      description "This section defines a RW.VCS rwcluster component";
      rwpb:msg-new VcsRwCluster;

      uses rwvcs-event-list;
    }
  }

  grouping rwvcs-rwvm {
    container rwvm {
      description "This section defines a RW.VCS rwvm component";
      rwpb:msg-new VcsRwVm;

      leaf pool-name {
        description "";
        type string;
      }

      leaf leading {
        description "If this vm is a leader, the instance name of the grouping it leads";
        type string;
      }

      uses rwvcs-event-list;
    }
  }

  grouping rwvcs-rwproc {
    container rwproc {
      description "This section defines a RW.VCS rwproc component";
      rwpb:msg-new VcsRwproc;

      list tasklet {
        description "List of tasklets to be run within this process";
        key "name";
        rwpb:msg-new RwprocTasklet;

        leaf name {
          description "Local description of the tasklet";
          type string;
        }

        leaf component-name {
          description "Component name of the tasklet";
          mandatory true;
          type leafref {
            path "../../../../component/component-name";
          }
        }

        leaf instance-id {
          description "If specified, the desired instance-id of tasklet component instance";
          type uint32;
        }

        uses rwvcs-variable-list;
      }
    }
  }

  grouping native-proc {
    container native-proc {
      rwpb:msg-new NativeProc;

      leaf environment {
        description "Runtime environment for native process";
        type string;
      }

      leaf exe-path {
        description "Path to native process executable";
        type string;
      }

      leaf args {
        description "Arguments to pass to native process";
        type string;
      }
    }
  }

  grouping rwvcs-rwtasklet {
    container rwtasklet {
      description "This section defines a RW.VCS rwtasklet component";
      rwpb:msg-new VcsRwTasklet;

      leaf plugin-directory {
        description "";
        type string;
      }

      leaf plugin-name {
        description "";
        type string;
      }

      leaf plugin-version {
        description "";
        type string;
      }
    }
  }

  grouping rwvcs-component-list {
    list component {
      description "This section defines the RiftWare virtual components";
      key "component-name";
      rwpb:application-request-point;

      leaf component-name {
        description "";
        type string;
      }

      choice component {
        case rwvcs-rwcolony {
          uses rwvcs-rwcolony;
        }
        case rwvcs-rwcluster {
          uses rwvcs-rwcluster;
        }
        case rwvcs-rwvm {
          uses rwvcs-rwvm;
        }
        case rwvcs-rwproc {
          uses rwvcs-rwproc;
        }
        case native-proc {
          uses native-proc;
        }
        case rwvcs-rwtasklet {
          uses rwvcs-rwtasklet;
        }
      }
    } // list component
  } // grouping rwvcs-component-list

  grouping bootstrap-phase {
    container bootstrap-phase {
      description "This section contains the bootstrap phase configuration";
      rwpb:msg-new BootstrapPhase;

      container rwtasklet {
        description "";
        rwpb:msg-new InitTasklet;

        leaf plugin-directory {
          description "";
          type string;
        }

        leaf plugin-name {
          description "";
          type string;
        }

        leaf plugin-version {
          description "";
          type string;
        }
      } // container rwtasklet

      container rwtrace {
        description "";
        rwpb:msg-new Trace;

        leaf enable {
          description "";
          mandatory false;
          type boolean;
        }
        choice destination {
          case console {}
          case file {
            leaf file {
              description "";
              type string;
            }
          }
          case memory-ring {}
          case syslog {}
        }
        leaf level {
          description "";
          mandatory false;
          type uint32 { range "0..9"; }
        }
        container filter {
          leaf file {
            description "";
            mandatory false;
            type string;
          }
          leaf line {
            description "";
            mandatory false;
            type uint32;
          }
        }
      } // container rwtrace

      leaf rwcal-type {
        description "RWCAL type";
        type string;
       }

      container zookeeper {
        leaf master-ip {
          description "IP address for master zookeeper";
          type string;
        }

        leaf unique-ports {
          description "Use zookeeper ports based on UID";
          type boolean;
        }

        leaf zake {
          description "Use zake to simulate the zookeeper in-memory";
          type boolean;
          default false;
        }

        leaf auto-instance-start {
          description "Value at which auto-assigned instance identifiers should start";
          type uint32;
          default 100;
        }
      }

      container rwcal-cloud {
        leaf cloud-type {
          description "Provider type for AWS EC2 US_EAST region";
          type rwcal-cloud-type;
        }

        leaf auth-key {
          description "User Key for authentication with cloud";
          type string;
        }

        leaf auth-secret {
          description "Secret key for authentication with cloud";
          type string;
        }

        leaf auth-url {
          description "URL for authentication with cloud provider.  [optional]";
          mandatory false;
          type string;
        }
      }

      container serf {
        leaf start {
          description "Start the Serf Agent";
          type boolean;
          default false;
        }
      }

    } // container bootstrap-phase
  } // grouping bootstrap-phase

  grouping init-phase {
    container init-phase {
      description "This section contains the init phase configuration";
      rwpb:msg-new InitPhase;

      container environment {
        description "This section contains all of the manifest environment variables";
        rwpb:msg-new Environment;

        uses rwvcs-variable-list;

        leaf component-name {
          description "String which will evaluate to the first component to be
            started by RWInit.  Similar to action/component-name but cannot be
            static.";
          type string;
        }

        leaf instance-id {
          description "String which will evaluate to the instance-id of the
            first component to be started by RWInit.  Similar to
            action/instance-id but cannot be static.";
          type string;
        }

        leaf instance-name {
          description "String which will evaluate to the instance-name of the
            first component to be started by RWInit.  Similar to
            action/instance-id but cannot be static.";
          type string;
        }
      }

      container rwcal {
        description "";

        list rwvm-pool {
          description "";
          key "name";
          rwpb:msg-new RwVmPool;

          leaf name {
            description "";
            type string;
          }

          choice rwvm-pool {
            case static-vm-list {
              list static-vm-list {
                description "";
                key "vm-name";

                leaf vm-name {
                  description "";
                  type string;
                }

                leaf vm-ip-address {
                  description "";
                  type rwt:ip-address;
                  rwpb:field-string-max 46;
                }
              }
            } // case static-vm-list
            case static-vm-range {
              description "";

              container static-vm-range{
                description "";

                container vm-name-range {
                  description "";

                  leaf base-name {
                    description "";
                    type string;
                    mandatory "true";
                  }

                  leaf low-index {
                    description "";
                    type uint32;
                    mandatory "true";
                  }

                  leaf high-index {
                    description "";
                    type uint32;
                    mandatory "true";
                  }
                }

                container vm-ip-range {
                  description "";

                  leaf low-addr {
                    description "";
                    type rwt:ip-address;
                    rwpb:field-string-max 46;
                    mandatory "true";
                  }
                  leaf high-addr {
                    description "";
                    type rwt:ip-address;
                    rwpb:field-string-max 46;
                    mandatory "true";
                  }
                }
              }
            } // case static-vm-range
          } // pool-type
        } // list rwvm-pool
      } // container rwcal

      container settings {
        description "This section contains the init phase settings for each RiftWare component";
        rwpb:msg-new Settings;

        container rwtrace {
          description "";
        } // container rwtrace

        container rwmsg {
          description "rwmsg settings";
          choice broker {
            case single-broker {
              container single-broker {
                  leaf enable-broker {
                    description "When this flag is set the tasklets are required to enable message broker";
                    type boolean;
                  }
                  leaf broker-port {
                    description "Port number where the broker is running";
                    type uint16;
                  }
                  leaf broker-host {
                    description "Host name where the broker is running";
                    type string;
                  }
              }
            }

            case multi-broker {
              container multi-broker {
                leaf enable { 
                  type boolean;
                  description "Enable one broker per VM.  Children of the VM will use the local broker";
                }
              }
            }
          }
        }

        container rwvcs {
          description "This section contains the init phase settings for each RiftWare component";
          rwpb:msg-new SettingsRwvcs;

          leaf collapse-each-rwvm {
            description "This configures each rwvm to collapse into a single real VM";
            type boolean;
          }

          leaf collapse-each-rwprocess {
            description "This configures each rwprocess to collapse into a single real process";
            type boolean;
          }

          leaf no-autostart {
            description "This disables the autostart section of the init-phase";
            type boolean;
          }

          leaf rwmain_path {
            description "Override for the path to the rwmain executable";
            type string;
          }

          leaf reaper_path {
            description "Override the path to the rwreaper executable";
            type string;
          }
        } // container rwvcs
      } // container settings
    } // container init-phase
  } // grouping init-phase

  container manifest {
    description "This section contains the entire manifest";
    rwpb:msg-new Manifest;

    leaf profile-name {
      description "The name of the profile to use within the manifest";
      type leafref {
        path "../profile/name";
      }
    }

    list profile {
      description "This list of manifest profiles";
      key name;
      rwpb:msg-new Profile;    // RwMProfile?

      leaf name {
        description "The name of this manifest profile";
        type string;
      }

      uses bootstrap-phase;
      uses init-phase;

      container inventory {
        description "This section contains all of the manifest inventory items";
        rwpb:msg-new Inventory;

        uses rwvcs-component-list;
      }
    }
  } // container manifest
}
