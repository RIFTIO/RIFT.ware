/* STANDARD_RIFT_IO_COPYRIGHT */

/**
 * @file rw-appmgr-log.yang
 * @author Aniruddha Atale
 * @date 08/11/2014
 * @brief RiftWare CLI for Appmgr Logging
 */

module rw-appmgr-log-d
{
  namespace "http://riftio.com/ns/riftware-1.0/rwappmgr-log";
  prefix "rwappmgrlog";

  import rw-pb-ext {
    prefix "rwpb";
  }

  import rw-notify-ext-d {
    prefix "rwnotify";
  }

  import rw-log-d {
    prefix "rwlog";
  }

  revision 2014-08-11 {
    description
      "Initial revision.";
    reference
      "RIFT Application Manager Logging";
  }

  /*
   * Common NwEPC Logs - ID space 00020000 - 00020100  
   */
  
  notification nwepc-log-debug {
    rwnotify:log-event-id 00020000;
      description
         "NwEPC Debug Log";
      uses rwlog:severity-debug;
      leaf log  {
        type string;
      }
  }
  notification nwepc-log-info {
    rwnotify:log-event-id 00020001;
      description
         "NwEPC Info Log";
      uses rwlog:severity-info;
      leaf log  {
        type string;
      }
  }
  notification nwepc-log-notice {
    rwnotify:log-event-id 00020002;
      description
         "NwEPC Notice Log";
      uses rwlog:severity-notice;
      leaf log  {
        type string;
      }
  }
  notification nwepc-log-warn {
    rwnotify:log-event-id 00020003;
      description
         "NwEPC Warning Log";
      uses rwlog:severity-warning;
      leaf log  {
        type string;
      }
  }
  notification nwepc-log-error {
    rwnotify:log-event-id 00020004;
      description
         "NwEPC Warning Log";
      uses rwlog:severity-error;
      leaf log  {
        type string;
      }
  }
  notification nwepc-log-critical {
    rwnotify:log-event-id 00020005;
      description
         "NwEPC Critical Log";
      uses rwlog:severity-critical;
      leaf log  {
        type string;
      }
  }
  notification nwepc-log-alert {
    rwnotify:log-event-id 00020006;
      description
         "NwEPC Alert Log";
      uses rwlog:severity-alert;
      leaf log  {
        type string;
      }
  }
  notification nwepc-log-emergency {
    rwnotify:log-event-id 00020007;
      description
         "NwEPC Emergency Log";
      uses rwlog:severity-emergency;
      leaf log  {
        type string;
      }
  }

  notification nwepc-packet-dump {
    rwnotify:log-event-id 00020008;
    description "Packet trace";
    uses rwlog:severity-info;
    uses rwlog:packet-info;
    leaf data {
      type binary;
    }
  }

  /*
   * END - Common NwEPC Logs - ID space 00020000 - 00020100  
   */

  /*
   * BEGIN UE NwEPC Logs - ID space 00020101 - 00020200  
   */
    notification nwepc-ue-log-debug {
    rwnotify:log-event-id 00020101;
      description
         "NwEPC Debug Log";
      uses rwlog:severity-debug;
      uses rwlog:group-call-id;
      leaf log  {
        type string;
      }      
  }
  notification nwepc-ue-log-info {
    rwnotify:log-event-id 00020102;
      description
         "NwEPC Info Log";
      uses rwlog:severity-info;
      
      uses rwlog:group-call-id;

      leaf log  {
        type string;
      }
  }
  notification nwepc-ue-log-notice {
    rwnotify:log-event-id 00020103;
      description
         "NwEPC Notice Log";
      uses rwlog:severity-notice;

      uses rwlog:group-call-id;
      
      leaf log  {
        type string;
      }
  }
  notification nwepc-ue-log-warn {
    rwnotify:log-event-id 00020104;
      description
         "NwEPC Warning Log";
      uses rwlog:severity-warning;

      uses rwlog:group-call-id;

      leaf log  {
        type string;
      }
  }
  notification nwepc-ue-log-error {
    rwnotify:log-event-id 00020105;
      description
         "NwEPC Warning Log";
      uses rwlog:severity-error;

      uses rwlog:group-call-id;

      leaf log  {
        type string;
      }
  }
  notification nwepc-ue-log-critical {
    rwnotify:log-event-id 00020106;
      description
         "NwEPC Critical Log";
      uses rwlog:severity-critical;
      uses rwlog:group-call-id;

      leaf log  {
        type string;
      }
  }
  notification nwepc-ue-log-alert {
    rwnotify:log-event-id 00020107;
      description
         "NwEPC Alert Log";
      uses rwlog:severity-alert;
      uses rwlog:group-call-id;

      leaf log  {
        type string;
      }
  }
  notification nwepc-ue-log-emergency {
    rwnotify:log-event-id 00020108;
      description
         "NwEPC Emergency Log";
      uses rwlog:severity-emergency;
      uses rwlog:group-call-id;

      leaf log  {
        type string;
      }
  }

  notification nwepc-ue-packet-dump {
    rwnotify:log-event-id 00020109;
    description 
        "Packet trace";
    uses rwlog:severity-info;
    uses rwlog:group-call-id;
    uses rwlog:packet-info;

    leaf data {
      type binary; 
    }
  }

  /*
   * END UE NwEPC Logs - ID space 00020101 - 00020200  
   */

  /*
   * BEGIN - EPC script space : 00020201 - 00020300 
   */
  grouping ue-script-session-params {
    leaf imsi { type string; }
    leaf imei { type string; }
    leaf msisdn { type string; }
    leaf apn { type string; }
    leaf pgw-ip { type string; }
    leaf sgw-ip { type string; }
  }

  notification ue-script-creating-session {
    rwpb:msg-new UeScriptCreatingSession;
    rwnotify:log-event-id 00020201;
    description "Creating a new session";
    uses rwlog:severity-info;
    uses rwlog:group-call-id;
    uses ue-script-session-params;
  }

  notification ue-script-create-session-failed {
    rwpb:msg-new UeScriptCreateSessionFailed;
    rwnotify:log-event-id 00020202;
    description "Experienced a failure while creating a new session";
    uses rwlog:severity-error;
    uses rwlog:group-call-id;
    uses ue-script-session-params;
    leaf log { type string; }
  }

  notification ue-script-delete-session-failed {
    rwpb:msg-new UeScriptDeleteSessionFailed;
    rwnotify:log-event-id 00020203;
    description "Experienced a failure while deleting a session";
    uses rwlog:severity-error;
    uses rwlog:group-call-id;
    uses ue-script-session-params;
    leaf log { type string; }
  }

  notification ue-script-get-session-status-failed {
    rwpb:msg-new UeScriptGetSessionStatusFailed;
    rwnotify:log-event-id 00020204;
    description "Experienced a failure while attempting to get session status";
    uses rwlog:severity-error;
    uses rwlog:group-call-id;
    uses ue-script-session-params;
    leaf log { type string; }
  }

  notification ue-script-session-created {
    rwpb:msg-new UeScriptSessionCreated;
    rwnotify:log-event-id 00020205;
    description "Session created";
    uses rwlog:severity-info;
    uses rwlog:group-call-id;
    uses ue-script-session-params;

    leaf netns-name { type string; }
    list ipv4-dns-entries {
      key "address";
      leaf address { type string; }
    }
    list ipv6-dns-entries {
      key "address";
      leaf address { type string; }
    }
  }

  notification ue-script-session-deleted {
    rwpb:msg-new UeScriptSessionDeleted;
    rwnotify:log-event-id 00020206;
    description "Session deleted";
    uses rwlog:severity-info;
    uses rwlog:group-call-id;
    uses ue-script-session-params;
  }

  notification ue-script-deleting-session {
    rwpb:msg-new UeScriptDeletingSession;
    rwnotify:log-event-id 00020207;
    description "Deleting a session";
    uses rwlog:severity-info;
    uses rwlog:group-call-id;
    uses ue-script-session-params;
  }

  notification ue-script-wait-session-state-timeout {
    rwpb:msg-new UeScriptWaitSessionStateTimeout;
    rwnotify:log-event-id 00020208;
    description "Experienced a timeout when waiting for a particular session state";
    uses rwlog:severity-error;
    uses rwlog:group-call-id;
    uses ue-script-session-params;
    leaf log { type string; }
  }

  /*
   * END - EPC script space : 00020201 - 00020300 
   */

  /*
   * BEGIN - EPC REST API space : 00020301 - 00020400
   */

  grouping rest-params {
    leaf ip { type string; }
    leaf port { type uint32; }
  }

  notification nwepc-rest-create-connection {
    rwpb:msg-new NwepcRestCreateConnection;
    rwnotify:log-event-id 00020301;
    description "Creating a connection to the nwepc REST server.";
    uses rwlog:severity-info;
    uses rest-params;
  }

  notification nwepc-rest-connection-error {
    rwpb:msg-new NwepcRestConnectionError;
    rwnotify:log-event-id 00020302;
    description "Failed to create a connection to the nwepc REST server.";
    uses rwlog:severity-error;
    uses rest-params;
    leaf log { type string; }
  }

  notification nwepc-rest-invalid-request-parameter {
    rwpb:msg-new NwepcRestInvalidRequestParameter;
    rwnotify:log-event-id 00020303;
    description "A parameter to create a session was invalid";
    uses rwlog:severity-error;
    uses rest-params;
    leaf log { type string; }
  }

  notification nwepc-rest-create-session-request-error {
    rwpb:msg-new NwepcRestCreateSessionRequestError;
    rwnotify:log-event-id 00020304;
    description "Request error when attempting to create a session";
    uses rwlog:severity-error;
    uses rest-params;
    leaf log { type string; }
    leaf url { type string; }
    leaf params { type string; }
  }

  notification nwepc-rest-delete-session-request-error {
    rwpb:msg-new NwepcRestDeleteSessionRequestError;
    rwnotify:log-event-id 00020305;
    description "Request error when attempting to delete a session";
    uses rwlog:severity-error;
    uses rest-params;
    leaf log { type string; }
    leaf url { type string; }
    leaf params { type string; }
  }

  notification nwepc-rest-create-session-response {
    rwpb:msg-new NwepcRestCreateSessionResponse;
    rwnotify:log-event-id 00020306;
    description "Got a response from CreateUeSession";
    uses rwlog:severity-debug;
    uses rest-params;
    leaf response { type string; }
  }

  notification nwepc-rest-delete-session-response {
    rwpb:msg-new NwepcRestDeleteSessionResponse;
    rwnotify:log-event-id 00020307;
    description "Got a response from DeleteUeSession";
    uses rwlog:severity-debug;
    uses rest-params;
    leaf response { type string; }
  }

  notification nwepc-rest-get-session-status-request-error {
    rwpb:msg-new NwepcRestGetSessionStatusRequestError;
    rwnotify:log-event-id 00020308;
    description "Request error when attempting to get session status";
    uses rwlog:severity-error;
    uses rest-params;
    leaf log { type string; }
    leaf url { type string; }
    leaf params { type string; }
  }

  notification nwepc-rest-get-session-status-response {
    rwpb:msg-new NwepcRestGetSessionStatusResponse;
    rwnotify:log-event-id 00020309;
    description "Got a response from GetUeSessionStatus";
    uses rwlog:severity-debug;
    uses rest-params;
    leaf response { type string; }
  }

  notification nwepc-rest-session-status-invalid-response {
    rwpb:msg-new NwepcRestSessionStatusInvalidResponse;
    rwnotify:log-event-id 00020310;
    description "Got an invalid response from GetUeSessionStatus";
    uses rwlog:severity-error;
    uses rest-params;
    leaf response { type string; }
    leaf log { type string; }
  }

  notification nwepc-rest-get-mme-stats-request-error {
    rwpb:msg-new NwepcRestGetMmeStatsRequestError;
    rwnotify:log-event-id 00020311;
    description "Request error when attempting to get mme stats";
    uses rwlog:severity-error;
    uses rest-params;
    leaf log { type string; }
    leaf url { type string; }
  }

  notification nwepc-rest-mme-stats-invalid-response {
    rwpb:msg-new NwepcRestMmeStatsInvalidResponse;
    rwnotify:log-event-id 00020312;
    description "Got an invalid response from /GetMmeEnodeBStats";
    uses rwlog:severity-error;
    uses rest-params;
    leaf response { type string; }
    leaf log { type string; }
  }

  notification nwepc-rest-get-mme-stats-response {
    rwpb:msg-new NwepcRestGetMmeStatsResponse;
    rwnotify:log-event-id 00020313;
    description "Got a response from GetMmeEnodeBStats";
    uses rwlog:severity-debug;
    uses rest-params;
    leaf response { type string; }
  }

  notification nwepc-rest-create-session-request {
    rwpb:msg-new NwepcRestCreateSessionRequest;
    rwnotify:log-event-id 00020314;
    description "Sending request to create a session";
    uses rwlog:severity-info;
    uses rest-params;
    leaf url { type string; }
    leaf params { type string; }
  }

  notification nwepc-rest-delete-session-request {
    rwpb:msg-new NwepcRestDeleteSessionRequest;
    rwnotify:log-event-id 00020315;
    description "Sending request to delete a session";
    uses rwlog:severity-info;
    uses rest-params;
    leaf url { type string; }
    leaf params { type string; }
  }

  notification nwepc-rest-get-session-status-request {
    rwpb:msg-new NwepcRestGetSessionStatusRequest;
    rwnotify:log-event-id 00020316;
    description "Sending request to get session status";
    uses rwlog:severity-info;
    uses rest-params;
    leaf url { type string; }
    leaf params { type string; }
  }

  notification nwepc-rest-get-mme-stats-request {
    rwpb:msg-new NwepcRestGetMmeStatsRequest;
    rwnotify:log-event-id 00020317;
    description "Sending request to get mme stats";
    uses rwlog:severity-info;
    uses rest-params;
    leaf url { type string; }
  }

  notification nwepc-rest-get-groupid-stats-request {
    rwpb:msg-new NwepcRestGetGroupidStatsRequest;
    rwnotify:log-event-id 00020318;
    description "Sending request to get group id stats";
    uses rwlog:severity-info;
    uses rest-params;
    leaf url { type string; }
    leaf params { type string; }
  }

  notification nwepc-rest-get-groupid-stats-error {
    rwpb:msg-new NwepcRestGetGroupidStatsRequestError;
    rwnotify:log-event-id 00020319;
    description "Request error when attempting to get groupid stats";
    uses rwlog:severity-error;
    uses rest-params;
    leaf log { type string; }
    leaf url { type string; }
  }

  notification nwepc-rest-get-groupid-stats-response {
    rwpb:msg-new NwepcRestGetGroupidStatsResponse;
    rwnotify:log-event-id 00020320;
    description "Got a response from GetGroupidStats";
    uses rwlog:severity-debug;
    uses rest-params;
    leaf response { type string; }
  }

  notification nwepc-rest-get-groupid-stats-invalid-response {
    rwpb:msg-new NwepcRestGetGroupidStatsInvalidResponse;
    rwnotify:log-event-id 00020312;
    description "Got an invalid response from /GetMmeEnodeBStats";
    uses rwlog:severity-error;
    uses rest-params;
    leaf response { type string; }
    leaf log { type string; }
  }


  /* SAEGW */
  notification saegw-rest-create-connection {
    rwpb:msg-new SaegwRestCreateConnection;
    rwnotify:log-event-id 00020350;
    description "Creating a connection to the saegw REST server.";
    uses rwlog:severity-info;
    uses rest-params;
  }

  notification saegw-rest-connection-error {
    rwpb:msg-new SaegwRestConnectionError;
    rwnotify:log-event-id 00020351;
    description "Failed to create a connection to the saegw REST server.";
    uses rwlog:severity-error;
    uses rest-params;
    leaf log { type string; }
  }

  notification saegw-rest-invalid-request-parameter {
    rwpb:msg-new SaegwRestInvalidRequestParameter;
    rwnotify:log-event-id 00020352;
    description "A parameter to create a session was invalid";
    uses rwlog:severity-error;
    uses rest-params;
    leaf log { type string; }
  }

  notification saegw-rest-delete-session-request {
    rwpb:msg-new SaegwRestDeleteSessionRequest;
    rwnotify:log-event-id 00020353;
    description "Sending request to delete a session";
    uses rwlog:severity-error;
    uses rest-params;
    leaf url { type string; }
    leaf params { type string; }
  }

  notification saegw-rest-delete-session-response {
    rwpb:msg-new SaegwRestDeleteSessionResponse;
    rwnotify:log-event-id 00020354;
    description "Got a response from DeleteSGWSession";
    uses rwlog:severity-debug;
    uses rest-params;
    leaf response { type string; }
  }

  notification saegw-rest-delete-session-request-error {
    rwpb:msg-new SaegwRestDeleteSessionRequestError;
    rwnotify:log-event-id 00020355;
    description "Request error when attempting to delete a session";
    uses rwlog:severity-error;
    uses rest-params;
    leaf log { type string; }
    leaf url { type string; }
    leaf params { type string; }
  }

  notification saegw-rest-get-session-status-request {
    rwpb:msg-new SaegwRestGetSessionStatusRequest;
    rwnotify:log-event-id 00020356;
    description "Sending request to get a session";
    uses rwlog:severity-error;
    uses rest-params;
    leaf url { type string; }
    leaf params { type string; }
  }

  notification saegw-rest-get-session-status-response {
    rwpb:msg-new SaegwRestGetSessionStatusResponse;
    rwnotify:log-event-id 00020357;
    description "Got a response from GetSGWSessionStatus";
    uses rwlog:severity-debug;
    uses rest-params;
    leaf response { type string; }
  }

  notification saegw-rest-get-session-status-request-error {
    rwpb:msg-new SaegwRestGetSessionStatusRequestError;
    rwnotify:log-event-id 00020358;
    description "Request error when attempting to get session status";
    uses rwlog:severity-error;
    uses rest-params;
    leaf log { type string; }
    leaf url { type string; }
    leaf params { type string; }
  }

  notification saegw-rest-get-session-status-invalid-response {
    rwpb:msg-new SaegwRestGetSessionStatusInvalidResponse;
    rwnotify:log-event-id 00020359;
    description "Got an invalid response from GetSGWSessionStatus";
    uses rwlog:severity-error;
    uses rest-params;
    leaf response { type string; }
    leaf log { type string; }
  }

  notification saegw-rest-get-stats-request {
    rwpb:msg-new SaegwRestGetStatsRequest;
    rwnotify:log-event-id 00020360;
    description "Sending request to get a session";
    uses rwlog:severity-error;
    uses rest-params;
    leaf url { type string; }
  }

  notification saegw-rest-get-stats-response {
    rwpb:msg-new SaegwRestGetStatsResponse;
    rwnotify:log-event-id 00020361;
    description "Got a response from GetSGWStats";
    uses rwlog:severity-debug;
    uses rest-params;
    leaf response { type string; }
  }

  notification saegw-rest-get-stats-request-error {
    rwpb:msg-new SaegwRestGetStatsRequestError;
    rwnotify:log-event-id 00020362;
    description "Request error when attempting to get session stats";
    uses rwlog:severity-error;
    uses rest-params;
    leaf log { type string; }
    leaf url { type string; }
  }

  notification saegw-rest-get-stats-invalid-response {
    rwpb:msg-new SaegwRestGetStatsInvalidResponse;
    rwnotify:log-event-id 00020363;
    description "Got an invalid response from GetSGWStats";
    uses rwlog:severity-error;
    uses rest-params;
    leaf response { type string; }
    leaf log { type string; }
  }

  /*
   * END - EPC REST API space : 00020301 - 00020400
   */
}
