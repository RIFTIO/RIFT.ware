/*
 * STANDARD_RIFT_IO_COPYRIGHT
 *
 */

module rwpnfd-d
{
  namespace "http://riftio.com/ns/riftware-1.0/rwpnfd";
  prefix "rwpnfd-d";

  import rw-manifest-d {
    prefix "rwmani";
  }

  import rwmano-types-d {
    prefix "rwmanotypes";
  }

  import rw-pb-ext {
    prefix "rwpb";
  }

  import rw-yang-types {
    prefix rwt;
  }

  import ietf-inet-types {
    prefix "inet";
  }

  import ietf-yang-types {
    prefix "yang";
  }

  revision 2014-10-27 {
    description
      "Initial revision. This YANG file defines 
       the Virtual Network Function (VNF)";
    reference
      "Derived from earlier versions of base YANG files";
  }

  container pnfd {
    description
        "Virtual Network Function Descriptor.";

    leaf name {
      description "PNF descriptor name.";
      type string;
    }

    leaf pnfd-id {
      description "UUID of the PNF descriptor.";
      type yang:uuid;
    }

    leaf vendor {
      description "Vendor name.";
      type string;
    }

    leaf description {
      description "Description of the VNF.";
      type string;
    }

    leaf version {
      description "Version";
      type string;
    }

    list connection-points {
      description
          "List for external connection points. Each PNF has one or more external
           connection points. As the name implies that external connection points 
           are used for connecting the VNF to other VNFs or to external networks.
           Each VNF exposes these connection points to the orchestrator. The 
           orchestrator can construct network services by connecting the
           connection points between different VNFs. The NFVO will use VLDs and 
           VNFFGs at the network service level to construct network services.";

      key "id";
      leaf id {
        description
            "Identifier for the external connection points";
        type uint32;
      }

      leaf cp-type {
        description
            "Type of the connection point.";
        type rwmanotypes:connection-point-type;
      }
    }
  }
}
