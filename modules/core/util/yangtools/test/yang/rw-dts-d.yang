/*
 * STANDARD_RIFT_IO_COPYRIGHT
 *
 */

module rw-dts-d
{
  namespace "http://riftio.com/ns/riftware-1.0/rwdtsd";
  prefix "rwdts";

  // new mode et al
  import rw-cli-ext { 
    prefix "rwcli";
  }

  import rw-pb-ext {
    prefix "rwpb";
  }

  description "RW.DTS yang definitions";

  revision 2014-10-01 {
    description "Initial revision";
    reference "None";
  }

  typedef state {
    type enumeration {
      enum unitialized;
      enum init;
      enum regn_complete;
      enum config;
      enum run;
    }
  }

  grouping router-memb-stats {
    list stats {
      rwpb:msg-new RouterMembStats;
      description " DTS Router Member stats";
      key "member-name";

      leaf member-name {
        description "Name of member whose stats are displayed";
        rwpb:field-inline "true";
        rwpb:field-string-max 256;
        type string;
      }
      leaf reg-prepare-called{
        type uint64;
      }
      leaf reg-precommit-called{
        type uint64;
      }
      leaf  reg-commit-called{
        type uint64;
      }
      leaf  reg-added{
        type uint64;
      }
    }
  }
  /* See also struct rwdts-router-stats-s, which is the non-pb-ugly runtime version of this data */
  grouping routerstats {
    list stats {
      rwpb:msg-new Routerstats;
      description "DTS router statistics";
      key "instance-uri";

      leaf "instance-uri" {
        rwpb:field-inline "true";
        rwpb:field-string-max yang;
        description "DTS broker instance";
          type string {
             length "1..64";
          }
      }

      leaf topx-begin {
        type uint64;
      }

      leaf topx-begin-tran {
        type uint64;
      }
      leaf topx-begin-notran {
        type uint64;
      }
      leaf topx-end {
        type uint64;
      }
      leaf topx-end-notran-success {
        type uint64;
      }
      leaf topx-end-notran-fail {
        type uint64;
      }
      leaf topx-end-commit {
        type uint64;
      }
      leaf topx-end-abort {
        type uint64;
      }
      leaf topx-end-fail {
        type uint64;
      }
      leaf-list topx-member-histo {
        min-elements 64;
        max-elements 64;
        rwpb:field-inline true;
        type uint64;
      }
      leaf subx-begin {
        type uint64;
      }
      leaf subx-begin-notran {
        type uint64;
      }
      leaf subx-retry {
        type uint64;
      }
      leaf-list subx-retry-histo {
        min-elements 64;
        max-elements 64;
        rwpb:field-inline true;
        type uint64;
      }
      leaf subx-retry-success {
        type uint64;
      }
      leaf subx-retry-failure {
        type uint64;
      }
      leaf subx-end {
        type uint64;
      }
      leaf subx-end-subcommit {
        type uint64;
      }
      leaf subx-end-subabort {
        type uint64;
      }
      leaf subx-end-suberr {
        type uint64;
      }
      leaf subx-end-notran-success {
        type uint64;
      }
      leaf subx-end-notran-fail {
        type uint64;
      }
      leaf prep-query-member-included {
        type uint64;
      }
      leaf prep-query-member-filtered {
        type uint64;
      }
      leaf req-sent {
        type uint64;
      }
      leaf req-bnc {
        type uint64;
      }
      leaf req-bnc-imm {
        type uint64;
      }
      leaf req-responded {
        type uint64;
      }
      leaf req-responded-async {
        type uint64;
      }
      leaf req-rcv-regist {
        type uint64;
      }
      leaf req-rcv-execute {
        type uint64;
      }
      leaf req-rcv-execute-topx {
        type uint64;
      }
      leaf req-rcv-execute-append {
        type uint64;
      }
      leaf req-rcv-execute-subx {
        type uint64;
      }
      leaf-list req-blocks-histo {
        min-elements 64;
        max-elements 64;
        rwpb:field-inline true;
        type uint64;
      }
      leaf req-rcv-end {
        type uint64;
      }
      leaf req-rcv-abort {
        type uint64;
      }
      leaf req-rcv-flush {
        type uint64;
      }
      leaf req-rcv-update-fake-table {
        type uint64;
      }
      leaf req-rcv-mbr-query-response {
        type uint64;
      }
      leaf req-rcv-mbr-regist {
        type uint64;
      }
      leaf more_sent {
        type uint64;
      }
      leaf incorrect_clientidx {
        type uint64;
      }
      leaf incorrect_routeridx {
        type uint64;
      }
      leaf xact-life-less-50-ms {
        type uint64;
      }
      leaf xact-life-less-100-ms {
        type uint64;
      }
      leaf xact-life-less-500-ms {
        type uint64;
      }
      leaf xact-life-less-1-sec {
        type uint64;
      }
      leaf xact-life-more-1-sec {
        type uint64;
      }
      leaf xact-prep-time-less-50-ms {
        type uint64;
      }
      leaf xact-prep-time-less-100-ms {
        type uint64;
      }
      leaf xact-prep-time-less-500-ms {
        type uint64;
      }
      leaf xact-prep-time-less-1-sec {
        type uint64;
      }
      leaf xact-prep-time-more-1-sec {
        type uint64;
      }
      leaf xact-pcom-time-less-50-ms {
        type uint64;
      }
      leaf xact-pcom-time-less-100-ms {
        type uint64;
      }
      leaf xact-pcom-time-less-500-ms {
        type uint64;
      }
      leaf xact-pcom-time-less-1-sec {
        type uint64;
      }
      leaf xact-pcom-time-more-1-sec {
        type uint64;
      }
      leaf xact-com-time-less-50-ms {
        type uint64;
      }
      leaf xact-com-time-less-100-ms {
        type uint64;
      }
      leaf xact-com-time-less-500-ms {
        type uint64;
      }
      leaf xact-com-time-less-1-sec {
        type uint64;
      }
      leaf xact-com-time-more-1-sec {
        type uint64;
      }
      leaf xact-abort-time-less-50-ms {
        type uint64;
      }
      leaf xact-abort-time-less-100-ms {
        type uint64;
      }
      leaf xact-abort-time-less-500-ms {
        type uint64;
      }
      leaf xact-abort-time-less-1-sec {
        type uint64;
      }
      leaf xact-abort-time-more-1-sec {
        type uint64;
      }
      leaf member-ct {
        type uint64;
      }
      leaf xact-ct {
        type uint64;
      }
    }
  }

  grouping routerxact {
    list transaction {
      rwpb:msg-new RouterXact;
      description "DTS Router xact related state";
      key "xid";
      leaf xid {
        rwpb:field-inline "true";
        rwpb:field-string-max yang;
        description "DTS Transaction id";
        type string {
          length "1..64";
        }   
      }   
      leaf handle {
        rwpb:field-inline "true";
        rwpb:field-string-max yang;
        description "DTS Transaction handle";
        type string {
          length "1..32";
        }   
      }   
      leaf state {
        description "DTS Transaction state";
        type string {
          length "1..32";
        }   
      }   
      leaf debug-info {
        description "DTS debug info";
        type string {
          length "1..128";
        }   
      }
      list trace-result {
        rwpb:msg-new RouterXacttrace;
        description "DTS Member xact related state";
        key "id";

        leaf id {
          type uint32;
          description "id";
        }

        leaf state-event {
          type string;
          rwpb:field-string-max 64;
          description "xact-state-event";
        }
      }
    }
  }

  grouping regstats {
    list stats {
      rwpb:msg-new Regstats;
      description "DTS member registration statistics";
      key "reg-id";

      leaf reg-id {
        rwpb:field-inline "true";
        description "DTS registration id";
        type uint32;
      }
      leaf num-prepare-rcvd {
        rwpb:field-inline "true";
        type uint64;
      }
      leaf num-precommit-rcvd {
        rwpb:field-inline "true";
        type uint64;
      }
      leaf num-commit-rcvd {
        rwpb:field-inline "true";
        type uint64;
      }
      leaf num-abort-rcvd {
        rwpb:field-inline "true";
        type uint64;
      }
      leaf num-prepare-cb-acked {
        rwpb:field-inline "true";
        type uint64;
      }
      leaf num-prepare-cb-nacked {
        rwpb:field-inline "true";
        type uint64;
      }
      leaf num-prepare-cb-async {
        rwpb:field-inline "true";
        type uint64;
      }
      leaf num-get-reqt-sent {
        rwpb:field-inline "true";
        type uint64;
      }
      leaf num-get-rsp-rcvd {
        rwpb:field-inline "true";
        type uint64;
      }
      leaf num-prepare-cb-invoked {
        rwpb:field-inline "true";
        type uint64;
      }
      leaf num-precommit-cb-invoked {
        rwpb:field-inline "true";
        type uint64;
      }
      leaf num-commit-cb-invoked {
        rwpb:field-inline "true";
        type uint64;
      }
      leaf num-abort-cb-invoked {
        rwpb:field-inline "true";
        type uint64;
      }
      leaf num-advises {
        rwpb:field-inline "true";
        type uint64;
      }
      leaf num-member-advise-rsp {
        rwpb:field-inline "true";
        type uint64;
      }
      leaf num-xact-create-objects {
        rwpb:field-inline "true";
        type uint64;
      }
      leaf num-xact-delete-objects {
        rwpb:field-inline "true";
        type uint64;
      }
      leaf num-xact-update-objects {
        rwpb:field-inline "true";
        type uint64;
      }
      leaf num-registrations {
        rwpb:field-inline "true";
        type uint64;
      }
      leaf num-deregistrations {
        rwpb:field-inline "true";
        type uint64;
      }
      leaf out-of-order-queries {
        type uint64;
        description "Total out of order queries";
      }
      leaf error-drop-advice {
        type uint64;
        description "OOS advice drop";
      }
      leaf error-drop-read {
        type uint64;
        description "OOS read response drop";
      }
      leaf not_ended {
        type uint64;
      }
      leaf num_response {
        type uint64;
      }
      leaf num_na_response {
        type uint64;
      }
      leaf num_ack_response {
        type uint64;
      }
      leaf num_nack_response {
        type uint64;
      }
      leaf num_async_response {
        type uint64;
      }
      leaf dispatch_async_response {
        type uint64;
      }
      leaf dispatch_response_immediate {
        type uint64;
      }
    }
  }
  grouping memberstats {
    list stats {
      rwpb:msg-new Memberstats;
      description "DTS member statistics";
      key "member-name";

      leaf member-name {
        type string;
        rwpb:field-string-max 256;
        description "Member Name";
      }

      leaf topx-begin {
        description "member side transaction begin";
        type uint64;
      }
      leaf topx-end {
        description "member side transaction ended";
        type uint64;
      }
      leaf internally-triggered {
        description "Num transactions triggered by DTS";
        type uint64;
      }
      leaf application-triggered {
        description "Num transactions triggered by application";
        type uint64;
      }

      leaf num-trans {
       type uint64;
       description "number of transactions";
      }
      leaf num-prepare {
        type uint64;
        description "prepare from router";
      }
      leaf num-pre-commit {
        type uint64;
        description "precommit from router";
      }
      leaf num-commit {
        type uint64;
        description "commit from router";
      }
      leaf num-abort {
        type uint64;
        description "abort from router";
      }
      leaf num-sub-commit {
        type uint64;
        description "sub commit from router";
      }
      leaf num-sub-abort {
        type uint64;
        description "sub abort from router";
      }
      leaf num-xact-create {
        type uint64;
        description "number of create transactions";
      }
      leaf num-xact-update {
        type uint64;
        description "number of updated transactions";
      }
      leaf num-xact-delete {
        type uint64;
        description "number of deleted transactions";
      }
      leaf num-commit-create {
        type uint64;
        description "number of create committed objects";
      }
      leaf num-commit-update {
        type uint64;
        description "number of updated committed objects";
      }
      leaf num-commit-delete {
        type uint64;
        description "number of deleted committed objects";
      }
      leaf num-reg {
        type uint64;
        description "number of registrations";
      }
      leaf num-dereg {
        type uint64;
        description "number of deregistrations";
      }
      leaf num-advice {
        type uint64;
        description "number of advises";
      }
      leaf num-regs-retrans {
        type uint64;
        description "number of reg retransmissions";
      }
      leaf num-advice-rsp {
        type uint64;
        description "number of advice response";
      }
      leaf num-prep-evt-init-state {
        type uint64;
        description "number of prepare events rcvd in init state";
      }
      leaf num-end-evt-init-state {
        type uint64;
        description "number of end events rcvd in init state";
      }
      leaf num-prep-evt-prep-state {
        type uint64;
        description "number of prepare events rcvd in prepare state";
      }
      leaf num-pcomm-evt-prep-state {
        type uint64;
        description "number of precommit events rcvd in prepare state";
      }
      leaf num-abort-evt-prep-state {
        type uint64;
        description "number of abort events rcvd in prepare state";
      }
      leaf num-qrsp-evt-prep-state {
        type uint64;
        description "number of query rsp events rcvd in prepare state";
      }
      leaf num-end-evt-prep-state {
        type uint64;
        description "number of end events rcvd in prepare state";
      }
      leaf num-prep-evt-pcomm-state {
        type uint64;
        description "number of prepare events rcvd in precommit state";
      }
      leaf num-pcom-evt-pcom-state {
        type uint64;
        description "number of precommit events rcvd in precommit state";
      }
      leaf num-com-evt-pcom-state {
        type uint64;
        description "number of commit events rcvd in precommit state";
      }
      leaf num-abor-evt-pcom-state {
        type uint64;
        description "number of abort events rcvd in precommit state";
      }
      leaf num-end-evt-comm-state {
        type uint64;
        description "number of end events rcvd in commit state";
      }
      leaf num-end-evt-abort-state {
        type uint64;
        description "number of end events rcvd in abort state";
      }
      leaf num-prepare-cb-exec {
        type uint64;
        description "number of prepare callbk executions";
      }
      leaf num-commit-cb-exec {
        type uint64;
        description "number of commit callbk executions";       
      }
      leaf num-pcommit-cb-exec {
        type uint64;
        description "number of precommit callbk executions";
      }
      leaf num-end-exec {
        type uint64;
        description "number of end executions";
      }
      leaf total-nontrans-queries {
        type uint64;
        description "Total non-transactional queries";
      }
      leaf total-trans-queries {
        type uint64;
        description "Total transactional queries";
      }
      leaf num-async-response {
        type uint64;
        description "Total async responses";
      }
      leaf num-na-response {
        type uint64;
        description "Total NA responses";
      }
      leaf num-ack-response {
        type uint64;
        description "Total ACK responses";
      }
      leaf num-nack-response {
        type uint64;
        description "Total NACK responses";
      }
      leaf num-query-response {
        type uint64;
        description "Total query responses";
      }
      leaf num-xact-rsp-dispatched {
        type uint64;
        description "Total responses dispatched";
      }
      leaf member-reg-advise-sent {
        type uint64;
        description "Reg advice sent";
      }
      leaf member-reg-advise-done {
        type uint64;
        description "Reg advice cb called";
      }
      leaf member-reg-advise-bounced {
        type uint64;
      }
      leaf more_received {
        type uint64;
      }
      leaf sent_keep_alive {
        type uint64;
      }
      leaf sent_credits {
        type uint64;
      }
      leaf destroyed_xact_with_more {
        type uint64;
      }
      leaf reroot_done {
        type uint64;
      }
    }
  }

  grouping rw-dts-info {
    list routers {
      config false;
      rwpb:msg-new Routerinfo;
      max-elements 128;
      description "DTS Router Status";
      list member-info {
        rwpb:msg-new RouterMemberInfo;
        description "DTS Member info at the router";
        key "name";
        leaf name {
          rwpb:field-inline "true";
          rwpb:field-string-max yang;
          description "DTS Member name";
          type string {
            length "1..64";
          }
        }
        list registration {
          rwpb:msg-new RouterRegn;
          description "DTS Router registration related state";
          key "id";
          leaf id {
            rwpb:field-inline "true";
            rwpb:field-string-max yang;
            description "DTS registration id";
            type string {
              length "1..64";
            }
          }
          leaf handle {
            rwpb:field-inline "true";
            rwpb:field-string-max yang;
            description "DTS registration handle";
            type string {
              length "1..32";
            }
          }
          leaf keyspec {
            rwpb:field-inline "true";
            rwpb:field-string-max yang;
            description "DTS registration keyspec";
            type string {
              length "1..64";
            }
          }
          leaf flags {
            rwpb:field-inline "true";
            rwpb:field-string-max yang;
            description "DTS registration flags";
            type string {
              length "1..8";
            }
          }
          leaf descriptor {
            rwpb:field-inline "true";
            rwpb:field-string-max yang;
            description "DTS registration descriptor";
            type string {
              length "1..32";
            }
          }
          leaf num-objects {
            description "Number of objects associated with this registration";
            type uint64;
          }
        }
        uses router-memb-stats;
      }
      uses routerxact;
      uses routerstats;
    }
  }

  grouping tracert {
    description "DTS Member tracert configuration";
    list tracert-filters {
      config true;
      rwpb:msg-new Tracert;
      key "id";
      leaf id {
        type uint32;
      }
      leaf path {
	rwpb:field-inline "true";
	rwpb:field-string-max yang;
	type string {
	  length "1..256";
        }
      }

      // tasklet parameters?
      // shard parameters?
      // sampling parameters?
      // ??

      // leaf target { enum  printf, logging, trace, dedicated queriable buffer, ?? }
    }

  }
  /* Member state and start */

  container dts {
    config true;
    rwcli:new-mode "dts";
    list member {
      config false;
      key "name";
      rwpb:msg-new MemberInfo;
      max-elements 128;
      description "DTS Member related stats and state";

      leaf name {
        rwpb:field-inline "true";
        rwpb:field-string-max yang;
        description "DTS Member name";
        type string {
          length "1..64";
        }
      }
      container state {
       rwpb:msg-new MemberState;
        description "Member related state";
        list transaction {
          rwpb:msg-new MemberXact;
          description "DTS Member xact related state";
          key "id";
          leaf id {
            rwpb:field-inline "true";
            rwpb:field-string-max yang;
            description "DTS Transaction id";
            type string {
              length "1..64";
            }
          }
          leaf handle {
            rwpb:field-inline "true";
            rwpb:field-string-max yang;
            description "DTS Transaction handle";
            type string {
              length "1..32";
            }
          }
          leaf state {
            description "DTS Transaction state";
            type string {
              length "1..32";
            }
          }
          leaf debug-info {
            description "DTS debug info";
            type string {
              length "1..128";
            }
          }
          list queries {
            rwpb:msg-new Queries;
            description "Related Queries";
            key "query-id";
            leaf query-id {
              description "Query index";
              type uint32;
            }
            list match-reg {
              rwpb:msg-new MatchReg;
              description "Matched registrations";
              key "reg-id";
              leaf reg-id {
                description "DTS Reg id";
                type uint32;
              }
            }
          } 
        }
        list registration {
          rwpb:msg-new MemberRegn;
          description "DTS Member registration related state";
          key "id";
          leaf id {
            description "DTS registration id";
            type uint32;
          }
          leaf handle {
            rwpb:field-inline "true";
            rwpb:field-string-max yang;
            description "DTS registration handle";
            type string {
              length "1..32";
            }
          }
          leaf keyspec {
            rwpb:field-inline "true";
            rwpb:field-string-max yang;
            description "DTS registration keyspec";
            type string {
              length "1..64";
            }
          }
          leaf flags {
            rwpb:field-inline "true";
            rwpb:field-string-max yang;
            description "DTS registration flags";
            type string {
              length "1..8";
            }
          }
          leaf descriptor {
            rwpb:field-inline "true";
            rwpb:field-string-max yang;
            description "DTS registration descriptor";
            type string {
              length "1..32";
            }
          }
          leaf num-objects {
            description "Number of objects associated with this registration";
            type uint64;
          }
          list cache-entry {
            rwpb:msg-new MemberCacheEntry;
            description "Each entry";
            key "pb";
            leaf pb {
              type string;
              rwpb:field-string-max 1024;
            }
          }
          uses regstats;
        }
     }
     list xact-trace {
      rwpb:msg-new Memberxacttrace;
      description "DTS xact trace";
      key "xact-id";

      list trace-result {
          rwpb:msg-new MemberXacttrace;
          description "DTS Member xact related state";
          key "id";

          leaf id {
           type uint32;
           description "xact-id";
          }
       
          leaf state-event {
           type string;
           rwpb:field-string-max 64;
           description "xact-state-event";
          } 
      }

      leaf xact-id {
        rwpb:field-inline "true";
        rwpb:field-string-max yang;
        description "Xact id";
        type string {
          length "1..256";
        }
      }

    }

     uses memberstats; 
    }
    uses rw-dts-info;

    uses tracert;
  }

  grouping rtr-ret-values {
    list rtr-reg {
       rwpb:msg-new RouterReg;
       description "DTS Router registration id";
       key "rtr-reg-id";

      leaf rtr-reg-id {
        type uint64;
      }
    }

    leaf rtr-id {
      type uint64;
    }

    leaf client-id {
      type uint64;
    }
  }

  grouping memb-reg-store {
    leaf rtr-id {
      type uint64;
    }

    leaf client-id {
      type uint64;
    }
  }

  grouping regist {
    leaf rtr-reg-id {
       rwpb:field-inline "true";
       description "DTS router assigned registration id";
       type uint64;
     }
     leaf keyspec {
       description "DTS registration keyspec";
       type binary;
     }
     leaf keystr {
       description "DTS registration keystr";
       type string;
     }
     leaf flags {
       rwpb:field-inline "true";
       description "DTS registration flags";
       type uint32;
     }
     leaf descriptor {
       rwpb:field-inline "true";
       rwpb:field-string-max yang;
       description "DTS registration descriptor";
       type string {
         length "1..32";
       }
     }
  }

  grouping regist-reg-id {
    list registration {
       rwpb:msg-new RouterInitRegnid;
       description "DTS Router registration related state";
       key "rtr-reg-id rtr-id";

       uses regist;
       uses memb-reg-store;
     }
  }

  grouping regist-keyspec {
    list registration {
       rwpb:msg-new RouterInitRegnkey;
       description "DTS Router registration related state";
       key "keystr flags";

       uses regist;
    }
  }

  container rtr-init-reg-id {
    config false;
    list member {
      key "name";
      rwpb:msg-new RtrInitMemberInfoid;
      max-elements 128;
      description "DTS Member related stats and state";
      config false;

      leaf name {
        rwpb:field-inline "true";
        rwpb:field-string-max yang;
        description "DTS Member name";
        type string {
          length "1..64";
        }
      }

      leaf all-regs {
        type empty;
      }

      uses regist-reg-id;

    }
  }
  grouping member-info {
    leaf name {
      rwpb:field-inline "true";
      rwpb:field-string-max yang;
      description "DTS Member name";
      type string {
        length "1..64";
      }
    }
    leaf state {
      type state;
    }
  }
  container rtr-init-reg-keyspec {
    config false;
    list member {
      key "name";
      rwpb:msg-new RtrInitMemberInfokey;
      max-elements 128;
      description "DTS Member related stats and state";
      config false;

      uses member-info;

      leaf all-regs {
        type empty;
      }
      uses regist-keyspec;
      uses memb-reg-store;
    }
  }

  container member-info-bcast {
    config false;
    uses member-info;
  }
}
