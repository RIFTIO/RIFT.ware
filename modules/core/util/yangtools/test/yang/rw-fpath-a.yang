/*
 * STANDARD_RIFT_IO_COPYRIGHT
 *
 */

module rw-fpath-a
{
  namespace "http://riftio.com/ns/riftware-1.0/rw-fpath";
  prefix "rw-fpath";
  
  import rw-base-a {
    prefix rwbase;
  }

  import rw-cli-ext { 
    prefix "rwcli";
  }

  import rw-pb-ext {
    prefix "rwpb";
  }

  import rw-yang-types {
    prefix "rwt";
  }

  revision 2014-03-31 {
    description
      "Initial revision.";
    reference
      "RIFT Trafgen Application";
  }

  typedef rwfpath-base-string {
    type string {
      length "1..256";
    }
  }

  typedef admin-state{
      type enumeration{
          enum down;
          enum up;
      }
  }
  
  typedef link-state{
      type enumeration{
          enum down;
          enum up;
      }
  }

  typedef lacp-state{
      type enumeration{
          enum down;
          enum up;
      }
  }
  
  typedef bundle-state-value{
      type enumeration{
          enum standby;
          enum active;
      }
  }

  typedef lacp-mode{
      type enumeration{
          enum none;
          enum passive;
          enum active;
      }
  }

  typedef lag-lb-mode{
      type enumeration{
          enum mac_ip;
          enum ip_trans;
          enum ip_trans_vsap;
      }
  }

  typedef mac-mode{
      type enumeration{
          enum active;
          enum follow;
          enum fixed;
      }
  }
  
  typedef template-type {
    description "Types of templates that are configured on ports";
    type enumeration {
      enum single-template;
      enum range-template;
      enum sequence-template;
      enum pcap;
    }
  }
  
  /*
    |       +-- rw ip-verion
    |       +-- rw protocol
    |       +-- rw destination-mac (..)
    |       +-- rw source-ip (...)
    |       +-- rw destination-ip(...)
    |       +-- rw source-port (...)
    |       +-- rw destination-port (...)
    |       +-- rw packet-size(...)
  */
  grouping range-param-attr {    
    leaf ip-version {
      type uint16;
    }
    leaf protocol{
      type uint16;
    }
    
    container destination-mac {
      leaf start {
        type rwt:mac-address;
        rwpb:field-string-max 18;
      }
      leaf minimum {
        type rwt:mac-address;
        rwpb:field-string-max 18;
      }
      leaf maximum {
        type rwt:mac-address;
        rwpb:field-string-max 18;
      }
      leaf increment {
        type uint16;
      }
      container dynamic{
        leaf gateway{
          description "Gateway IP address";
          type rwt:ip-address;
          rwpb:field-string-max 46;
        }
      }
    }
    
    container source-ip {
      leaf start {
        description "Starting source IP address";
        type rwt:ip-address;
        rwpb:field-string-max 46;
      }
      leaf minimum {
        description "Minimum source IP address";
        type rwt:ip-address;
        rwpb:field-string-max 46;
      }
      leaf maximum {
        description "Maximum source IP address";
        type rwt:ip-address;
        rwpb:field-string-max 46;
      }
      leaf increment {
        type uint16;
      }
    }
    
    container destination-ip {
      leaf start {
        description "Starting destination IP address";
        type rwt:ip-address;
        rwpb:field-string-max 46;
      }
      leaf minimum {
        description "Minimum destination IP address";
        type rwt:ip-address;
        rwpb:field-string-max 46;
      }
      leaf maximum {
        description "Maximum destination IP address";
        type rwt:ip-address;
        rwpb:field-string-max 46;
      }
      leaf increment {
        type uint16;
      }
    }
    
    container source-port {
      leaf start {
        type rwt:port-number;
      }
      leaf minimum {
        type rwt:port-number;
      }
      leaf maximum {
        type rwt:port-number;
      }
      leaf increment {
        type uint16;
      }
    }
    
    container destination-port {
      leaf start {
        type rwt:port-number;
      }
      leaf minimum {
        type rwt:port-number;
      }
      leaf maximum {
        type rwt:port-number;
      }
      leaf increment {
        type uint16;
      }
    }
    
    container packet-size {
      leaf start {
        type uint16;
      }
      leaf minimum {
        type uint16;
      }
      leaf maximum {
        type uint16;
      }
      leaf increment {
        type uint16;
      }
    }
  }

  /*
    |       +-- rw ip-verion
    |       +-- rw protocol
    |       +-- rw destination-mac 
    |       +-- rw source-ip 
    |       +-- rw destination-ip
    |       +-- rw source-port 
    |       +-- rw destination-port 
    |       +-- rw packet-size
  */
  grouping template-attr {
    leaf ip-version {
      description "IP version";
      type uint16;
    }
    leaf protocol{
      type uint16;
    }
    leaf packet-size {
      description "Size of packet to be generated";
      type uint32;
    }
    leaf source-port {
      description "IP L4 Source Port of the generated packet";
      type uint16;
    }
    leaf destination-port {
      description "IP L4 Destination Port of the generated packet";
      type uint16;
    }
    leaf destination-ip{
      description "destination ip address of the generated packet";
      type rwt:ip-address;
      rwpb:field-string-max 46;
    }
    leaf source-ip{
      description "source ip address of the generated packet";
      type rwt:ip-prefix-non-canonical;
      rwpb:field-string-max 64;
    }
    container destination-mac{
      container dynamic{
        leaf gateway{
          description "Gateway IP Address";
          type rwt:ip-address;
          rwpb:field-string-max 46;
        }
      }
      leaf mac{
        rwpb:field-string-max 18;
        type rwt:mac-address;
      }
    }
  }

  grouping transmit-param-attr {
    leaf descr-string {
      description "description comment for trafgen";
      rwpb:field-string-max 32;
      type string;
    }

    leaf tx-rate {
      description "Transmit rate as percentage of port speed";
      type uint32;
    }
    leaf packet-count {
      description 
          "Total number of packets to be generated(default to unlimited)";
      type uint32;
    }
    leaf burst-size {
      description "Burst size  in no of packets be generated";
      type uint32;
    }
    leaf tx-cycles {
      description "transmit cycle of the gernated traffic";
      type uint32;
    }

    container transmit-mode {
      description
        "Transmit mode for the packets to be sent. It can be
        single|range|sequence|pcap <file>. In single mode, the same packet
        will be sent out continuously. In the range mode, depending on the
        params configured, the destination-ip, sourceip, sourceport,
        destination-port will keep getting changed. In the sequence mode,
        you can enter as many as 16 sequences of packets that need to be sent
        continuously. Pcap mode needs a filename. The file is parsed to get
        the packets and these packets are sent out.";
      leaf single {
        type empty;
      }
      leaf range {
        type empty;
      }
      leaf sequence {
        type empty;
      }
      container pcap {
        leaf file{
          rwpb:field-string-max 256;
          type string;
        }
      }
    }
  }
  grouping lacppdu-info{
      rwpb:msg-new LacppduInfo;
      leaf systemid {
          description "System-d of the actor";
          type rwt:mac-address;
          rwpb:field-string-max 17;
      }
      leaf systemprio{
          type uint32;
      }
      leaf key{
          type uint32;
          description "actor key";
      }
      leaf portid{
          type uint32;
          description "actor portid";
      }
      leaf portprio{
          type uint32;
      }
      leaf state{
          type bits {
              bit aggregate {
                  position 0;
              }
              bit timeout {
                  position 1;
              }
              bit sync {
                  position 2;
              }
              bit collecting {
                  position 3;
              }
              bit distributing {
                  position 4;
              }
              bit defaulted {
                  position 5;
              }
              bit expired {
                  position 6;
              }
          }
          rwpb:field-string-max 8;
      }
  }
  grouping vlan-grouping{
      list vlan{
          key "id";
          rwcli:new-mode "  vlan";
          rwpb:field-inline-max yang;
          max-elements 32;

          leaf id {
              type uint32;
          }
          leaf descr-string {
              description "description comment for port";
              rwpb:field-inline "true";
              rwpb:field-string-max 32;
              type string;
          }
          
          leaf open {
              description "open the specified port";
              type empty;
          }
          
          leaf shutdown {
              description "Administrative shutdown of the port";
              type empty;
          }
      }
  }
  
  augment /rwbase:colony {
      // Work around for Jira: 1879
    list bundle-ether {
      rwcli:new-mode " bundle-ether";
      key "name";
      rwpb:field-inline-max yang;
      max-elements 32;
      
      leaf name {
          description "Name of the bundle";
          rwpb:field-inline "true";
          rwpb:field-string-max 64;
          type string;
      }

      leaf descr-string {
        description "description comment for port";
        rwpb:field-inline "true";
        rwpb:field-string-max 32;
        type string;
      }

      leaf open {
          description "open the specified port";
          type empty;
      }
      leaf mtu{
          description "MTU of the port";
          type uint32;
      }
      leaf shutdown {
          description "Administrative shutdown of the port";
          type empty;
      }
      container lacp{
          container system{
              leaf priority{
                  description "configure the lacp priority for the system(colony)";
                  type uint32;
              }
              leaf id{
                  description "local system ID used by the Link Aggregation Control Protocol (LACP)";
                  type rwt:mac-address;
                  rwpb:field-string-max 18;    
              }
          }
      }
      container bundle{
          container minimum-active{
              leaf links{
                  description "Minimum number of active links to bring up the bundle";
                  type uint32;
              }
          }
          container maximum-active{
              leaf links{
                  description "Maximum number of active links in the bundle";
                  type uint32;
              }
          }
          leaf load-balance{
              description "packet contents to use for load-balancing";
              type lag-lb-mode;
          }
          leaf mac-mode{
              description "Mac-mode for 1:1 redundancy";
              type mac-mode;
          }
      }
      uses vlan-grouping;
    }
    list port {
      rwcli:new-mode " port";
      key "name";
      rwpb:field-inline-max yang;
      max-elements 32;
      
      leaf name {
        description "Name of the port";
        rwpb:field-inline "true";
        rwpb:field-string-max 64;
        type string;
      }

      leaf descr-string {
        description "description comment for port";
        rwpb:field-inline "true";
        rwpb:field-string-max 32;
        type string;
      }

      container open {
        description "open the specified port";
        container application{
          description "Application that is using this port. Default is IPFP";
          container ip-fastpath {
            presence true;
            leaf virtual-fabric {
              type empty;
            }
          }
          leaf trafgen {
            type empty;
          }  
        }
      }
      leaf mtu{
          description "MTU of the port";
          type uint32;
      }
      leaf shutdown {
          description "Administrative shutdown of the port";
          type empty;
      }
      choice member-mode{
          case bundled{
              container bundle{
                  leaf name{
                      description "Name of the port";
                      rwpb:field-inline "true";
                      rwpb:field-string-max 64;
                      type string;
                  }
                  leaf mode{
                      type lacp-mode;
                  }
                  container port{
                      leaf priority{
                          type uint32;
                      }
                  }
              }
              container lacp{
                  leaf fast-switchover{
                      description "Used to diable the wait-while timer in LACP state machine";
                      type empty;
                  }
                  container period{
                      leaf receive{
                          description "Time interval (in milliseconds) for receiving LACP packets when LACP short period is enabled.100-1000ms";
                          type uint32;
                      }
                      leaf transmit{
                          description "Time interval (in milliseconds) for transmitting LACP packets when LACP short period is enabled.";
                          type uint32;
                      }
                  }
              }
          }
          case non-bundled{
              uses vlan-grouping;
          }
      }
      leaf receive-q-length {
        description "No of receive queues for the port. default is 2";
        type uint32;
      }
      
      container descriptors {
        leaf rx-size {
          description "Size of rx descriptor ring. default is 256";
          type uint32;
        }
        leaf tx-size {
          description "Size of tx descriptor ring. default is 256";
          type uint32;
        }
      }
      // Flow control configuration for the port
      container flow-control {
        leaf flow-type {
          description "none|rx|tx|both";
          type string;
          rwpb:field-inline "true";
          rwpb:field-string-max 5;
        }
        leaf high-watermark {
          type uint32;
        }
        leaf low-watermark {
          type uint32;
        }
        leaf pause-time {
          type uint32;
        }
        leaf send-xon {
          description 
              "whether or no to send XON, when flow control status change 
              to no flow control";
          type enumeration {
            enum off { value 0; }
            enum on  { value 1; }
          }
        }
      }

      container trafgen {
        rwcli:new-mode "trafgen";
        rwpb:msg-new ConfigTrafgen;
        rwpb:msg-flat "true";

        container transmit-params {
          rwcli:new-mode "transmit-param";
          description
            "This is a template for specifying the attributes for packet 
                generation such as transmit rate, packet count, burst size ...";
          
          uses transmit-param-attr;
        }

        container receive-param  {
          rwcli:new-mode "receive-param";
          description
            "This is a template for specifying the attributes for 
                packet generation such as transmit rate, packet count, 
                burst size ...";
          
          container receive-echo {
            leaf on {
              type empty;
            }
          }
        }

        choice template-type {
          case range-template {
            container range-template {
              rwcli:new-mode "range-template";
              description
                  "This is a template for specifying the contents of packets 
                generated by trafgen application. This template allows the 
                specfiying the ranges for destination mac address, source ip 
                address, destination ip address, source port, destination 
                port and packet sizes. For each of these ranges minimum and 
                maximum values can be specified. The increment value 
                specifies how the values are picked between minimum and 
                maximum values. It is also possible to specify and ip version 
                and L3 protocol type using this template.";
              uses range-param-attr;
            }
          }
          case sequence-template {
            container sequence-template {
              rwcli:new-mode "sequence_template";
              description
                  "This is a template for specifying the contents of packets 
                generated by trafgen application. This template allows 
                specification of ip version, l3 protocol, destination mac, 
                source ip, destination ip, source port, destination port 
                and packet size. Note that this template is a list and can 
                contain one or more streams of such packets. If the list size 
                is one, all the generated packets will have the same 
                attributes.";
              
              list  sequence {
                key "id";
                rwcli:new-mode "sequence-id";
                rwpb:field-inline-max yang;
                max-elements 32;
                leaf id {
                  description "Sequence Id";
                  type uint32;
                }              
                uses template-attr;
              }
            }
          }
          case single-template {
            container single-template {
              rwcli:new-mode "single-template";
              
              description
                  "This template allows specifying the contents of packets 
                generated by trafgen application. This template supports 
                specfiying the destination mac address, source ip address, 
                destination ip address, source port, destination port and 
                packet sizes. It is also possible to specify and ip version
                and L3 protocol type using this template.";

              uses template-attr;
            }
          }

        }
      }
    }
    uses network-context-state;
    container bundle-state{
        rwpb:msg-proto-max-size "215208";
        config false;
        list bundle-ether{
            rwpb:field-inline "true";
            key "name";
            rwpb:field-inline-max yang;
            max-elements 32;
            leaf name {
                description "Name of the bundle";
                rwpb:field-inline "true";
                rwpb:field-string-max 64;
                type string;
            }
            leaf admin-state{
                type admin-state;
            }
            leaf oper-state{
                type link-state;
            }
            leaf lport-id{
                type uint32;
            }
            leaf mtu{
                description "MTU of the port";
                type uint32;
            }
            leaf system-priority{
                description "The lacp priority for the system(colony)";
                type uint32;
            }
            leaf system-id{
                description "System ID used by the Link Aggregation Control Protocol (LACP)";
                rwpb:field-inline "true";
                type rwt:mac-address;
                rwpb:field-string-max 18;    
            }
            leaf bundle-mac{
                description "MAC used by the Link Aggregation Control Protocol (LACP)";
                rwpb:field-inline "true";
                type rwt:mac-address;
                rwpb:field-string-max 18;    
            }
            leaf min-active-links{
                description "Minimum number of active links to bring up the bundle";
                type uint32;
            }
            leaf max-active-links{
                description "Maximum number of active links in the bundle";
                type uint32;
            }
            leaf load-balance{
                description "packet contents to use for load-balancing";
                type lag-lb-mode;
            }
            leaf mac-mode{
                description "Mac-mode for 1:1 redundancy";
                type mac-mode;
            }
            list members{
                rwpb:field-inline "true";
                key "name";
                rwpb:field-inline-max yang;
                max-elements 32;
                leaf name {
                    description "Name of the bundle";
                    rwpb:field-inline "true";
                    rwpb:field-string-max 64;
                    type string;
                }
                leaf lportid{
                    type uint32;
                }
                leaf admin-state{
                    type admin-state;
                }
                leaf link-state{
                    description "Admin State";
                    type link-state;
                }
                leaf lacp-mode{
                    description "Admin State";
                    type  lacp-mode;
                }
                leaf lacp-state{
                    description "Admin State";
                    type lacp-state;
                }
                leaf bundle-state{
                    description "Admin State";
                    type bundle-state-value;
                }
                leaf priority{
                    type uint32;
                }
                leaf rx-interval{
                    type uint32;
                }
                leaf tx-interval{
                    type uint32;
                }
                leaf fast-switchover{
                    type uint32;
                }
                leaf mac{
                    rwpb:field-inline "true";
                    type rwt:mac-address;
                    rwpb:field-string-max 18;    
                }
            }
        }
    }
    list fastpath{
        rwpb:field-inline-max yang;
        max-elements 1;
        rwpb:msg-new FastpathState;
        key "instance";
        
        leaf instance {
            type uint32;
            description "Virtual-Fabric Port Identifier";
        }
        
        uses network-context-state;

        uses kernel-stats;
    }

    container trafgen-info {
        rwpb:msg-new RwTrafgenInfo;
        rwpb:msg-flat true;
        config false;

        list port {
            rwpb:field-inline-max yang;
            max-elements 32;
            
            key "name";
            
            leaf name {
                type string;
                rwpb:field-string-max 256;
                description "Port Name";
            }
            
            leaf id {
                type rwt:port-number;
                description "Port Identifier";
            }
            leaf descr-string {
                description "description comment for load balancer";
                rwpb:field-string-max 32;
                type string;
            }
            leaf tx_state {
                type enumeration {
                    enum off { value 0; }
                    enum on { value 1; }
                }
                description "Current state of Trafgen trasmit off/on";
            }
            
            leaf tx_rate {
                type uint32;
                description "Configured Tx Rate";
            }
            leaf tx_count {
                type uint32;
                description "Counfigured Tx Count";
            }
            leaf pkt_size {
                type uint32;
                description "size of packet transmitted on the port";
            }
            leaf tx_burst {
                type uint32;
                description "transmit burst size on the port";
            }
            leaf tx_mode {
                type template-type;
                description 
                    "Packet generation mode template configured for the port";
            }
            leaf packet-count {
                type uint32;
                description "transmit packet count for the port";
            }
            leaf tx-cycles {
                type uint32;
                description "transmit tx cycles for the port";
            }
            leaf src_l4_port {
                type uint32;
                description "Source L4 port of Transmitted packet";
            }
            leaf dst_l4_port {
                type uint32;
                description "Destination L4 port of Transmitted packet";
            }
            leaf src_ip_address {
                type rwt:ip-address;
                rwpb:field-string-max 46;
                description "source ip address of Transmitted packet";
            }
            leaf dst_ip_address {
                type rwt:ip-address;
                rwpb:field-string-max 46;
                description "destination ip address of Transmitted packet";
            }
            leaf src_mac_address {
                type rwt:mac-address;
                rwpb:field-string-max 18;
                description "source mac address of Transmitted packet";
            }
            leaf dst_mac_address {
                type rwt:mac-address;
                rwpb:field-string-max 18;
                description "destination mac address of Transmitted packet";
            }
        }
    }
    
    container port-state {
        config false;
        
        container info {
            rwpb:msg-new RwPortInfo;
            rwpb:msg-flat true;
            
            list port {
                rwpb:field-inline-max yang;
                max-elements 32;
                
                key "name";
                
                leaf name {
                    type string;
                    rwpb:field-string-max 256;
                    description "Port Name";
                }
                
                leaf id {
                    type rwt:port-number;
                    description "Port Identifier";
                }
                
                leaf descr-string {
                    description "description comment for port";
                    rwpb:field-string-max 32;
                    type string;
                }
                leaf state {
                    
                    type enumeration {
                        enum down { value 0; }
                        enum up   { value 1; }
                    }
                    description "Port State, Up/Down";
                }
                
                leaf speed {
                    type uint32;
                    description "Port speed in Mbps";
                }
                leaf duplex {
                    type enumeration {
                        enum half-duplex { value 0; }
                        enum full-duplex { value 1; }
                    }
                    description "Port duplex, half-duplex/full-duplex";
                }
                
                leaf app-name {
                    type string;
                    rwpb:field-string-max 32;
                    description "Name of the application running on the port";
                }
                leaf receive-queues {
                    type rwt:gauge32;
                    description "Number of receice queues on the port";
                }
                leaf transmit-queues {
                    type rwt:gauge32;
                    description "Number of transmit queues on the port";
                }
                leaf numa-socket {
                    type int32;
                    description "NUMA socket to which port PCI is attached";
                }
                leaf fastpath-instance {
                    type int32;
                    description "FastPath Instance managing the port";
                }
            }
        }
        
        container queues {
            rwpb:msg-new RwPortQueueStat;
            rwpb:msg-flat true;
            rwpb:msg-proto-max-size "156840";
                        
            list port {
                rwpb:field-inline-max yang;
                max-elements 32;
                
                key "name";
                
                leaf name {
                    type string;
                    rwpb:field-string-max 256;
                    description "Port Name";
                }
                
                leaf id {
                    type rwt:port-number;
                    description "Port Identifier";
                }
                leaf fastpath-instance {
                    type int32;
                    description "FastPath Instance managing the port";
                }
                list rx_queue {
                    rwpb:field-inline-max yang;
                    max-elements 16;
                    
                    key "rx_qid";
                    
                    uses rx_queue_stats;
                }
                
                list tx_queue {
                    rwpb:field-inline-max yang;
                    max-elements 40;
                    
                    key "tx_qid";
                    
                    uses tx_queue_stats;
                }
            }
        }
        container lacp-info{
            rwpb:msg-new RwPortLacpinfo;
            rwpb:msg-flat true;
            list port {
                rwpb:field-inline-max yang;
                max-elements 32;
                
                key "name";
                
                leaf name {
                    type string;
                    rwpb:field-string-max 256;
                    description "Port Name";
                }
                leaf lport-id{
                    type uint32;
                    description "Corresponding logical port id";
                }
                
                leaf bundle-name{
                    type string;
                    rwpb:field-string-max 64;
                    description "Bundle Name";
                }
                leaf bundle-lportid{
                    type uint32;
                    description "Corresponding Bundle logical port id";
                }
                leaf port-mac{
                    description "Port MAC address";
                    type rwt:mac-address;
                    rwpb:field-string-max 17;
                }
                container actor{
                    uses lacppdu-info;
                }
                container partner{
                    uses lacppdu-info;
                }
                leaf lacp-mux-state{
                    type string;
                    rwpb:field-string-max 20;
                }
                leaf selected-state{
                    type string;
                    rwpb:field-string-max 20;
                }
            }
        }
        container lacp-counters{
            rwpb:msg-new RwPortLacpstat;
            rwpb:msg-flat true;
            list port {
                rwpb:field-inline-max yang;
                max-elements 32;
                
                key "name";
                
                leaf name {
                    type string;
                    rwpb:field-string-max 256;
                    description "Port Name";
                }
                leaf lport-id{
                    type uint32;
                    description "Corresponding logical port id";
                }
                
                leaf bundle-name{
                    type string;
                    rwpb:field-string-max 64;
                    description "Bundle Name";
                }
                leaf bundle-lportid{
                    type uint32;
                    description "Corresponding Bundle logical port id";
                }
                container lacppdu{
                    leaf rx{
                        type uint32;
                        description "Number of lacp-pdus received on the port";
                    }
                    leaf tx{
                        type uint32;
                        description "Number of lacp-pdus sent on the port";
                    }
                    leaf errors{
                        type uint32;
                        description "Number of lacp-pdus errors on the port";
                    }
                    leaf nobuf{
                        type uint32;
                        description "Number of lacp-pdus errors on the port";
                    }
                }
                container marker{
                    leaf rx{
                        type uint32;
                        description "Number of marker received on the port";
                    }
                    leaf tx{
                        type uint32;
                        description "Number of marker sent on the port";
                    }
                    leaf errors{
                        type uint32;
                        description "Number of marker errors on the port";
                    }
                    leaf nobuf{
                        type uint32;
                        description "Number of marker errors on the port";
                    }
                }
            }
        }
        container counters {
            rwpb:msg-new RwPortStat;
            rwpb:msg-flat true;
                        
            list port {
                rwpb:field-inline-max yang;
                max-elements 32;
                
                key "name";
                
                leaf name {
                    type string;
                    rwpb:field-string-max 256;
                    description "Port Name";
                }
                
                leaf id {
                    type rwt:port-number;
                    description "Port Identifier";
                }
                leaf fastpath-instance {
                    type int32;
                    description "FastPath Instance managing the port";
                }
                leaf state {
                    type enumeration {
                        enum down { value 0; }
                        enum up { value 1; }
                    }
                    description "Port State, UP(1)/Down(0)";
                }
                leaf speed {
                    type uint32;
                    description "Port speed in Mbps";
                }
                leaf duplex {
                    type enumeration {
                        enum half-duplex { value 0; }
                        enum full-duplex { value 1; }
                    }
                    description "Port duplex, half-duplex/full-duplex";
                }
                leaf rx-rate-pps {
                    type rwt:gauge32;
                    description "Rx Rate(pps)";
                }
                leaf tx-rate-pps {
                    type rwt:gauge32;
                    description "Tx Rate(pps)";
                }
                leaf rx-rate-mbps {
                    type rwt:gauge32;
                    description "Rx Rate(Mbps)";
                }
                leaf tx-rate-mbps {
                    type rwt:gauge32;
                    description "Tx Rate(Mbps)";
                }
                leaf input-errors {
                    type rwt:zero-based-counter32;
                    description "Input Errors";
                }
                leaf output-errors {
                    type rwt:zero-based-counter32;
                    description "Output Errors";
                }
                leaf input-packets {
                    type rwt:zero-based-counter64;
                    description "Input packets";
                }
                leaf output-packets {
                    type rwt:zero-based-counter64;
                    description "Output packets";
                }
                leaf input-bytes {
                    type rwt:zero-based-counter64;
                    description "Total In bytes(MB)";
                }
                leaf output-bytes {
                    type rwt:zero-based-counter64;
                    description "Total Out Bytes(MB)";
                }
            }
        }
    }

    container virtual-fabric {
        config false;
        rwpb:msg-new VirtualFabricInfo;
        rwpb:msg-flat true;
        rwpb:msg-proto-max-size "5663064";
        list fastpath{
            rwpb:field-inline-max yang;
            max-elements 1;
            rwpb:msg-proto-max-size "5663024";
            
            key "instance";
            
            leaf instance {
                type uint32;
                description "FPATH instance number";
            }
            container statistics {
                leaf vf_pkt_rcvd {
                    type uint64;
                }
                leaf vf_pkt_rcv_dropped {
                    type uint64;
                }
                leaf vf_pkt_rcv_port_tx {
                    type uint64;
                }
                leaf vf_pkt_rcv_policy_fwd {
                    type uint64;
                }
                leaf vf_pkt_rcv_in_lookup {
                    type uint64;
                }
                leaf vf_pkt_rcv_dlvr_app {
                    type uint64;
                }
                leaf vf_pkt_rcv_dlvr_kern {
                    type uint64;
                }
                leaf vf_pkt_rcv_ip_reasm {
                    type uint64;
                }
                leaf vf_pkt_rcv_echo {
                    type uint64;
                }
                leaf vf_pkt_xmit {
                    type uint64;
                }
                leaf vf_pkt_tx_dropped {
                    type uint64;
                }
                leaf vf_pkt_tx_port_tx {
                    type uint64;
                }
                leaf vf_pkt_tx_policy_fwd {
                    type uint64;
                }
                leaf vf_pkt_tx_in_lookup {
                    type uint64;
                }
                leaf vf_pkt_tx_dlvr_app {
                    type uint64;
                }
                leaf vf_pkt_tx_dlvr_kern {
                    type uint64;
                }
                leaf vf_pkt_tx_ip_reasm {
                    type uint64;
                }
                leaf vf_pkt_tx_echo {
                    type uint64;
                }
            }
            list vfap {
                rwpb:field-inline-max yang;
                max-elements 128;
                
                key "vfapid";
                
                leaf vfapid {
                    type uint32;
                    description "Virtual-Fabric Port Identifier";
                }
                leaf groupid {
                    type uint32;
                    description "Virtual-Fabric Port Identifier";
                }
                leaf local-vfap {
                    type enumeration {
                        enum No { value 0; }
                        enum Yes  { value 1; }
                    }
                    description "This is my local VFAP";
                }
                list ip{
                    rwpb:field-inline-max yang;
                    max-elements 16;
                    
                    key "address";
                    
                    leaf address {
                        type rwt:ip-address;
                        rwpb:field-string-max 46;
                        description "IP addess bound to the VFAP";
                    }
                    leaf echo-request-sent {
                        type uint64;
                        description "Number of VF-Echo Request packet sent to this VFAP";
                    }
                    leaf echo-response-rcvd {
                        type uint64;
                        description "Number of VF-Echo Response Packet received from this VFAP";
                    }
                    leaf echo-request-rcvd {
                        type uint64;
                        description "Number of VF-Echo Request Packet received from this VFAP";
                    }
                    leaf echo-response-sent {
                        type uint64;
                        description "Number of VF-Echo Response Packet sent to this VFAP";
                    }
                    leaf average-transit-latency {
                        type uint64;
                        description "Average transit latency from this VFAP";
                    }
                }
            }
            list vsap {
                rwpb:field-inline-max yang;
                max-elements 128;
                
                key "vsapid";
                
                leaf vsapid {
                    type uint32;
                    description "Virtual Serivce Access Point Identifier";
                }
                leaf groupid {
                    type uint32;
                    description "Virtual Serivce Access Point Identifier";
                }
                
                list vfap {
                    rwpb:field-inline-max yang;
                    max-elements 32;
                    
                    key "vfapid";
                    
                    leaf vfapid {
                        type uint32;
                        description "Virtual-Fabric Port Identifier";
                    }
                    list ip {
                        rwpb:field-inline-max yang;
                        max-elements 16;
                        
                        key "address";
                        
                        leaf address {
                            type rwt:ip-address;
                            rwpb:field-string-max 46;
                            description "IP addess bound to the VFAP";
                        }
                    }
                }
                
                leaf local-vsap {
                    type enumeration {
                        enum No { value 0; }
                        enum Yes  { value 1; }
                    }
                    description "This is my local VSAP";
                }
                
                leaf pkts-rcvd {
                    type uint64;
                    description "Number of Packet received for this VSAP";
                }
                leaf pkts-sent {
                    type uint64;
                    description "Number of Packets sent for this VSAP";
                }
            }
        }
    }
   
    container ip-classifier {
        config false;
        rwpb:msg-new IpClassifierInfo;
        rwpb:msg-flat true;
        rwpb:msg-proto-max-size "3407336";
        list fastpath {
            rwpb:field-inline-max yang;
            max-elements 1;
            
            key "instance";
            
            leaf instance {
              type uint32;
              description "FPATH instance number";
            }

            container statistics {
              leaf num_signatures {
                 type uint32;
              }
              leaf num_local_hashbins {
                 type uint32;
              }
              leaf num_flows {
                 type uint32;
              }
              leaf signature_add {
                 type uint64;
              }
              leaf signature_delete {
                 type uint64;
              }
              leaf signature_add_fail {
                 type uint64;
                }
              leaf signature_match {
                type uint64;
              }
              leaf signature_app_dlvr {
                type uint64;
              }
              leaf flow_add {
                type uint64;
              }
              leaf flow_delete {
                type uint64;
              }
              leaf flow_add_lbin {
                type uint64;
              }
              leaf flow_add_rbin_fwd {
                type uint64;
              }
              leaf flow_add_rbin_rcvd {
                type uint64;
              }
              leaf flow_add_fail {
                type uint64;
              }
              leaf flow_delete_lbin {
                type uint64;
              }
              leaf flow_delete_rbin_fwd {
                type uint64;
              }
              leaf flow_delete_rbin_rcvd {
                type uint64;
              }
              leaf flow_delete_fail {
                type uint64;
              }
              leaf flow_lookup {
                type uint64;
              }
              leaf flow_lookup_lbin {
                type uint64;
              }
              leaf flow_lookup_rbin_fwd {
                type uint64;
              }
              leaf flow_lookup_rbin_rcvd {
                type uint64;
              }
              leaf flow_lookup_success {
                type uint64;
              }
              leaf flow_lookup_rbin_nosig {
                type uint64;
              }
           }

           list signatures {                                                                                                          
              rwpb:field-inline-max yang;
              max-elements 32;
            
              key "signature-id";
            
              leaf signature-id {
                type uint32;
                description "Signature ID";
              }
              leaf priority {
                type uint32;
              }
              leaf flow-type {
                type uint32;
              }
              leaf ncid {
                type uint32;
              }
              leaf ip-address {
                type rwt:ip-address;                                                
                rwpb:field-string-max 46;
              }
              leaf app_id {
                type uint32;
              }
              leaf appdata {
                type uint32;
              }
              leaf length {
                type uint32;
              }
              leaf key-val {
                type string; 
                rwpb:field-string-max 128;
              }
              leaf key-mask {
                type string;
                rwpb:field-string-max 128;
              }
           }

           list flows {                                                                                                                                                                                                                                       
              rwpb:field-inline-max yang;
              max-elements 128;
            
              key "flow-id";
            
              leaf flow-id {
                type uint64;
                description "Flow Id";
              }
              leaf flow-type {
                type uint32;
              } 
              leaf vsapid {
                type uint32;
              }
              leaf appdata {
                type uint32;
              }
              leaf ncid {
                type uint32;
              }
              leaf port-meta {
                type uint32;
              }
              leaf ip-protocol {
                type uint8;
              }
              leaf ip-src-address {
                type rwt:ip-address;                                                
                rwpb:field-string-max 46;
              }
              leaf ip-dst-address {
                type rwt:ip-address;                                                
                rwpb:field-string-max 46;
              }
              leaf ip-src-port {
                type uint8;
              }
              leaf ip-dst-port {
                type uint8;
              }
          }
        }
    }


   container external-app-plugin {
        config false;
        rwpb:msg-new ExtPpPlugin;
        rwpb:msg-flat true;
        rwpb:msg-proto-max-size "3407336";
        list fastpath {
            rwpb:field-inline-max yang;
            max-elements 1;

            key "instance";

            leaf instance {
              type uint32;
              description "FPATH instance number";
            }

            container statistics {
              leaf num_flow_cfg {
                 type uint32;
              }
              leaf num_server_lb {
                 type uint32;
              }
              leaf num_client {
                 type uint32;
              }
              leaf num_lb_vsapid {
                 type uint32;
              }
              leaf lb_sent_to_vsap {
                 type uint64;
              }
              leaf lb_drop_no_vsap_for_slice {
                 type uint64;
              }
              leaf srv_lb_drop_no_vsap {
                 type uint64;
              }
              leaf srv_rnat_drop_no_binding {
                 type uint64;
              }
            }

            list clients {
              rwpb:field-inline-max yang;
              max-elements 64;
             
              key "index";

              leaf index {
                 type uint32;
              }
              leaf ncid {
                 type uint32;
              }
              leaf ip-address {
                type rwt:ip-address;                                                
                rwpb:field-string-max 46;
              }
              leaf port {
                 type uint16;
              }

              leaf protocol {
                type enumeration {
                  enum udp { value 0; }
                  enum tcp  { value 1; }
                }
              }
              leaf vsapid {
                 type uint32;
              }
              leaf reverse_fwd {
                 type uint64;
              }
            }

            list servers {
              rwpb:field-inline-max yang;
              max-elements 64;

              key "index";

              leaf index {
                 type uint32;
              }
              leaf ncid {
                 type uint32;
              }
              leaf ip-address {
                type rwt:ip-address;
                rwpb:field-string-max 46;
              }
              leaf port {
                 type uint16;
              }

              leaf protocol {
                type enumeration {
                  enum udp { value 0; }
                  enum tcp  { value 1; }
                }
              }
              leaf vsapid {
                 type uint32;
              }
              leaf nat-ip-address {
                type rwt:ip-address;
                rwpb:field-string-max 46;
              }
              leaf num-bindings {
                 type uint32;
              }
              leaf forward_nat_fwd {
                 type uint64;
              }
              leaf reverse_nat_fwd {
                 type uint64;
              }
            }
        }
    }
   container logical-port {
        config false;
        rwpb:msg-new LportInfo;
        rwpb:msg-flat true;
        rwpb:msg-proto-max-size "154196";

        list fastpath{
            rwpb:field-inline-max yang;
            max-elements 1;
            rwpb:msg-proto-max-size "154156";
            
            key "instance";
            
            leaf instance {
                type uint32;
                description "Virtual-Fabric Port Identifier";
            }
            
            list lport{
                key "id";
                
                max-elements 128;
                leaf name {
                    type string;
                    rwpb:field-string-max 64;
                    description "Logical Port Name";
                }
                
                leaf id {
                    type uint32;
                    description "lport-id";
                }

                leaf context{
                    type string;
                    rwpb:field-string-max 64;
                    rwpb:field-inline "true";
                    description "Context Name";
                }
                
                leaf portname{
                    type string;
                    rwpb:field-string-max 64;
                    rwpb:field-inline "true";
                    description "Corresponding physical port";
                }
                
                leaf kni{
                    type string;
                    rwpb:field-string-max 64;
                    rwpb:field-inline "true";
                    description "Corresponding kernel interface name";
                }
                
                leaf fabric{
                    type enumeration {
                        enum No { value 0; }
                        enum Yes  { value 1; }
                    }
                    description "logical port representing virtual-fabric port";
                }
                
                leaf lport-type{
                    type string;
                    rwpb:field-string-max 64;
                    description "Logical Port Type";
                }
                
                leaf lport-state{
                    type enumeration {
                        enum DOWN { value 0; }
                        enum UP  { value 1; }
                    }
                    description "Operation State of the logical port";
                }

                container rx{
                    uses network-packet-counters-direction;
                }
                container tx{
                    uses network-packet-counters-direction;
                }
            }      
        }
    }
    container load-balancer {
        config false;
        rwpb:msg-new LoadbalancerInfo;
        rwpb:msg-flat true;
           list fastpath{
            rwpb:field-inline-max yang;
            max-elements 1;
            
            key "instance";
            
            leaf instance {
                type uint32;
                description "Virtual-Fabric Port Identifier";
            }
            list worker {
                rwpb:field-inline-max yang;
                max-elements 32;
                
                key "id";
                
                leaf id {
                    type uint32;
                    description "Load Balancer worker id";
                }
                leaf fwd-bindings {
                    type uint32;
                    description "number of current forward direction bindings";
                }
                leaf rev-bindings {
                    type uint32;
                    description "number of current reverse direction bindings";
                }
                leaf fwd-pkt-received {
                    type uint64;
                    description "total number of forward direction packets received";
                }
                leaf fwd-pkt-xmit {
                    type uint64;
                    description "total number of forward direction packets transmitted";
                }
                leaf fwd-pkt-drop {
                    type uint64;
                    description "total number of forward direction packets dropped";
                }
                leaf rev-pkt-received {
                    type uint64;
                    description "total number of reverse direction packets received";
                }
                leaf rev-pkt-xmit {
                    type uint64;
                    description "total number of reverse direction packets transmitted";
                }
                leaf rev-pkt-drop {
                    type uint64;
                    description "total number of reverse direction packets dropped";
                }
            }
           }
    }
  }
  /*
    +--rw network-context
    +-- rw lb-profile* [name]
    |   +-- rw name
    |   +-- rw destination-nat* [real-ip]
    |       +-- rw real-ip
    |       +-- rw tcp-port
    |       +-- rw udp-port
    |       +-- rw source-ip
    +-- rw load-balancer*[name]
    +-- rw name
    +-- virtual-ip
    +-- tcp-port
    +-- udp-port
    +-- lb-profile
  */
  augment /rwbase:colony/rwbase:network-context {
    list interface {
      rwpb:msg-new ConfigIpInterface;
      rwpb:msg-flat true;
      rwpb:field-inline-max "yang";
      rwcli:new-mode "ip-interface";
          
      max-elements 32;
          
      key "name";
        
      leaf name {
          description "interface name";
          type string;
          rwpb:field-string-max 64;
      }
      container interface-type{
          description "Interface type. defaults to an interface bound to port/vlan";
          leaf loopback{
              type empty;
          }
      }
      list ip {
        rwpb:field-inline-max "yang";
        max-elements 32;
        key "address";
          
        leaf address {
            description "ipv4 address assigned to the interface";
            type rwt:ipv4-prefix-non-canonical;
            rwpb:field-string-max 18;
        }
      }
      list ipv6 {
        rwpb:field-inline-max "yang";
        max-elements 32;
        key "address";
          
        leaf address {
            description "ipv6 address assigned to the interface";
            type rwt:ipv6-prefix-non-canonical;
            rwpb:field-string-max 64;
        }
      }
      
      container bind{
          leaf port{
              description "port name to bind the interface to";
              rwpb:field-string-max 64;
              type string;
          }
          
          leaf vlan{
              description "vlan tag of the port to which the interface is bound";
              type uint16;
          }
          container bundle-ether{
              leaf name{
                  description "Name of the port";
                  rwpb:field-inline "true";
                  rwpb:field-string-max 64;
                  type string;
              }
              leaf vlan{
                  description "vlan tag of the port to which the interface is bound";
                  type uint16;    
              }
          }
              
      }
    }
    
    container ip {
      rwpb:msg-new ConfigIp;
      rwpb:msg-flat true;
          
      list route {
        description "static IPv4 route configured";
        rwpb:msg-new ConfigRoute;
        rwpb:msg-flat true;
        rwpb:field-inline-max "yang";
              
        max-elements 32;

        key "prefix";
              
        leaf prefix {
            description "static IPv4 route prefix";
            type rwt:ipv4-prefix-non-canonical;
            rwpb:field-string-max 18;
        }
        leaf gateway {
            description "gateway address of the static route";
            type rwt:ipv4-address;
            rwpb:field-string-max 15;
        }
        leaf interface-name {
            description "interface of the static route";
            type string;
            rwpb:field-inline "true";
            rwpb:field-string-max 64;
        }
      }
      list arp {
        rwpb:msg-new ConfigArp;
        rwpb:msg-flat true;
        rwpb:field-inline-max "yang";

        max-elements 32;

        key "address";
              
        leaf address{
            description "IPv4 address for the static arp entry";
            type rwt:ipv4-address;
            rwpb:field-string-max 15;
        }
        leaf macaddress {
            description "MAC address for the static arp entry";
            type rwt:mac-address;
            rwpb:field-string-max 17;
        }
        leaf interface-name {
            description "Interface Name for the static arp entry";
            type string;
            rwpb:field-string-max 64;
        }
      }
      list nat-pool {
          rwpb:msg-new ConfigNatPool;
          rwpb:msg-flat true;
          rwpb:field-inline-max "yang";
          
          max-elements 32;
          
          key "name";
          
          leaf name{
              description "pool name for the nat-pool";
              type string;
              rwpb:field-string-max 64;
          }
          leaf prefix {
              description "prefix for the nat-pool";
              type rwt:ipv4-prefix-non-canonical;
              rwpb:field-string-max 18;
          }
      }
    }
    container ipv6 {
      rwpb:msg-new ConfigIpv6;
      rwpb:msg-flat true;
          
      list route{
        rwpb:msg-new ConfigRoute6;
        rwpb:msg-flat true;
        rwpb:field-inline-max "yang";
              
        max-elements 32;

        key "prefix";
              
        leaf prefix {
            description "static IPv6 route prefix";
            type rwt:ipv6-prefix-non-canonical;
            rwpb:field-string-max 64;
        }
        leaf gateway{
            description "gateway address for the IPv6 static route";
            type rwt:ipv6-address;
            rwpb:field-string-max 46;
        }
        leaf interface-name{
            description "interface of the static route";            
            type string;
            rwpb:field-string-max 64;
        }
      }
      list neighbor {
        rwpb:msg-new ConfigNeighbor;
        rwpb:msg-flat true;
        rwpb:field-inline-max "yang";

        max-elements 32;

        key "address";
              
        leaf address{
            description "IPv6 address for the static neighbor entry";
            type rwt:ipv6-address;
            rwpb:field-string-max 46;
        }
        leaf macaddress{
            description "MAC address for the static neighbor entry";
            type rwt:mac-address;
            rwpb:field-string-max 17;
        }
        leaf interface-name{
            description "Interface name for the static neighbor entry";
          type string;
          rwpb:field-string-max 64;
        }
      }
      list nat-pool {
          rwpb:msg-new ConfigNat6Pool;
          rwpb:msg-flat true;
          rwpb:field-inline-max "yang";
          
          max-elements 32;
          key "name";
          
          leaf name{
              description "pool name for the nat-pool";
              type string;
              rwpb:field-string-max 64;
          }

          leaf prefix {
              description "prefix for the nat-pool";
              type rwt:ipv6-prefix-non-canonical;
              rwpb:field-string-max 64;
          }
      }
    }


    list  lb-profile {
      rwpb:msg-new ConfigLbProfile;
      rwcli:new-mode "lb-profile";
      rwpb:msg-flat true;
      rwpb:field-inline "true";
      rwpb:field-inline-max yang;

      key "name";
      max-elements 32;
      
      leaf name {
        description "Name of lb-profile";
        rwpb:field-string-max 256;
        type string;
      }

      leaf descr-string {
        description "description comment for lb-profile";
        rwpb:field-string-max 32;
        type string;
      }

      list destination-nat {
        key "real-ip";
        rwpb:field-inline-max yang;
        max-elements 32;
        
        leaf real-ip {
          type rwt:ip-address;
          rwpb:field-string-max 46;
        }
        leaf tcp-port {
          type uint16;
        }
        leaf udp-port {
          type uint16;
        }
        leaf source-ip {
          type rwt:ip-address;
          rwpb:field-string-max 46;
        }
      }
    }

    list load-balancer {
      rwpb:msg-new ConfigLoadBalancer;
      rwcli:new-mode "load-balancer";
      rwpb:field-inline "true";
      rwpb:msg-flat true;
      rwpb:field-inline-max yang;

      key "name";
      max-elements 32;
      
      leaf name {
        description "Name of load-balancer";
        rwpb:field-string-max 256;
        type string;
      }

      leaf descr-string {
        description "description comment for load balancer";
        rwpb:field-string-max 32;
        type string;
      }


      leaf virtual-ip {
        type rwt:ip-address;
        rwpb:field-string-max 46;
      }
      leaf tcp-port {
        type uint16;
      }
      leaf udp-port {
        type uint16;
      }
      leaf lb-profile {
        rwpb:field-string-max 256;
        type string;
      }
    }

    list ip-receiver-application {
      rwpb:msg-new ConfigReceiverApp;
      rwcli:new-mode "ip-receiver-app";
      rwpb:field-inline "true";
      rwpb:msg-flat true;
      rwpb:field-inline-max yang;

      key "name";
      max-elements 32;

      leaf name {
        description "Name of IP Receiver App";
        rwpb:field-string-max 256;
        type string;
      }

      leaf descr-string {
        description "description comment for receiver app";
        rwpb:field-string-max 32;
        type string;
      }

      leaf ip-address {
        description "Address of the receiver application";
        type rwt:ip-address;
        rwpb:field-string-max 46;
      }
      leaf protocol {
        description "Layer 4 protocol for IP";
        type enumeration {
          enum udp { value 0; }
          enum tcp  { value 1; }
        }
      }
      leaf port {
        description "L4 port number of the receiver application";
        type uint16;
      }
     leaf action {
        description "Action to be performed on received packet";
        type enumeration {
          enum drop { value 0; }
          enum echo { value 1; }
        }
      }
    }
  }

  
  
  /* Imported from the data files */
  grouping ip-nexthops{
    list nexthops{
      max-elements 10;
      leaf type{
          description "Type of the nexthop";
          type rwt:ip-address;
          rwpb:field-string-max 20;
      }
      leaf ifindex{
          description "Ifindex of the nexthop";
          type uint32;
      }
      leaf gateway{
          description "Gateway Address of the nexthop";
          type rwt:ip-address;
          rwpb:field-string-max 46;
      }
      leaf lportname{
          description "Interface Name of the nexthop";
          type string;
          rwpb:field-string-max 64;
      }
    }
  }
  
  grouping ip-nhrec-info{
      list nhrec{
          rwpb:field-inline-max yang;
          max-elements 32;
        
          key "nhrec";
          
          leaf nhrec{
          type uint32;
        }
        uses ip-nexthops;
      }
  }
  

  grouping rx_queue_stats {
    leaf rx_qid {
      type uint32;
      description "Receive Queue Id";
    }
    leaf rx-rate-pps {
      type rwt:gauge32;
      description "Rx Rate(pps)";
    }
    leaf rx-rate-mbps {
      type rwt:gauge32;
      description "Rx Rate(Mbps)";
    }
    leaf input-packets {
      type rwt:zero-based-counter64;
      description "Input packets";
    }
    leaf input-bytes-MB {
      type rwt:zero-based-counter64;
      description "Total In bytes(MB)";
    }
  }

  grouping tx_queue_stats {
    leaf tx_qid {
      type uint32;
      description "Receive Queue Id";
    }
    leaf tx-rate-pps {
      type rwt:gauge32;
      description "Tx Rate(pps)";
    }
    leaf tx-rate-mbps {
      type rwt:gauge32;
      description "Tx Rate(Mbps)";
    }
    leaf output-errors {
      type rwt:zero-based-counter32;
      description "Output Errors";
    }
    leaf output-packets {
      type rwt:zero-based-counter64;
      description "Output packets";
    }
    leaf output-bytes-MB {
      type rwt:zero-based-counter64;
      description "Total Out Bytes(MB)";
    }
  }

  grouping ip-family{
      container nexthop-record {
          rwpb:msg-new NhrecInfo;
          rwpb:msg-flat true;
          uses ip-nhrec-info;
      }
      list interface{
          rwpb:msg-new IpIntfInfo;
          rwpb:msg-flat true;
          
          rwpb:field-inline-max yang;
          max-elements 32;
          
          key "lportid";
              
          leaf lportid {
              description "Ifindex of the Interface in the kernel";
              type uint32;
          }
          leaf name{
              description "Configured Name of the Interface";
              type string;
              rwpb:field-string-max 64;
          }
          leaf platform-name{
              description "Interface Name in the kernel";
              type string;
              rwpb:field-inline "true";
              rwpb:field-string-max 64;
          }
          leaf state{
              description "State of the Interface";
              type string;
              rwpb:field-inline "true";
              rwpb:field-string-max 10;
          }
          list ip {
              rwpb:msg-new IpIntfAddrInfo;
              rwpb:msg-flat true;
              
              rwpb:field-inline-max yang;
              max-elements 32;
              leaf address{
                  description "IP address of the interface";
                  type rwt:ip-address;
                  rwpb:field-string-max 46;
              }
          }
      }
      list route {
          rwpb:msg-new IpRouteInfo;
          rwpb:msg-flat true;
          
          rwpb:field-inline-max yang;
          max-elements 32;
          
          key "prefix";
          
          leaf prefix {
              description "IP prefix for the route";
              type rwt:ip-prefix-non-canonical;
              rwpb:field-string-max 64;
          }
          leaf protocol{
              description "Protocol";
              type rwt:ip-address;
              rwpb:field-string-max 20;
          }
          leaf nhrec{
              description "Nexthop handle index";
              type uint32;
          }
          uses ip-nexthops;
      }
  }

  grouping network-packet-counters-direction{
      container packet-counters-direction{
          rwpb:msg-new PacketCountersDirection;
          rwpb:msg-flat true;
          leaf total-wire-packets{
              description "Total number of wire packets of all packet sizes and all address-family (IPv4, IPv6...)";
              type rwt:zero-based-counter64;
          }
          leaf total-vf-packets{
              description "Total number of virtual fabric packets of all packet sizes and all address-family (IPv4, IPv6...)";
              type rwt:zero-based-counter64;
          }
          leaf total-kni-packets{
              description "Total number of kni packets of all packet sizes and all address-family (IPv4, IPv6...)";
              type rwt:zero-based-counter64;
          }
          leaf total-app-packets{
              description "Total number of app packets of all packet sizes and all address-family (IPv4, IPv6...)";
              type rwt:zero-based-counter64;
          }
          leaf total-ipv4_packets{
              description "Total number of IPv4 packets of all packet size";
              type rwt:zero-based-counter64;
          }
          leaf total-ipv6_packets{
              description "Total number of IPv6 packets of all packet size";
              type rwt:zero-based-counter64;
          }
          leaf total-64-packets{
              description "Total number of packets of 64-128 size packets";
              type rwt:zero-based-counter64;
          }
          leaf total-128-packets{
              description "Total number of packets of 128-256 size packets";
              type rwt:zero-based-counter64;
          }
          leaf total-256-packets{
              description "Total number of packets of 256-512 size packets";
              type rwt:zero-based-counter64;
          }
          leaf total-512-packets{
              description "Total number of packets of 512-1024 size packets";
              type rwt:zero-based-counter64;
          }
          leaf total-1024-packets{
              description "Total number of packets of 1024-2048 size packets";
              type rwt:zero-based-counter64;
          }
          leaf total-2048-packets{
              description "Total number of packets of > 2048 size packets";
              type rwt:zero-based-counter64;
          }
          leaf fwd-miss-packets{
              description "Total number of packets sent to the kernel for logical-port/route misses";
              type rwt:zero-based-counter64;
          }
          leaf neigh-miss-packets{
              description "Total number of packets sent to the kernel for arp/neighbor misses";
              type rwt:zero-based-counter64;
          }
          leaf forme-packets{
              description "Total number of packets destined for local address (no-ip-classification";
              type rwt:zero-based-counter64;
          }
          leaf flow-packets{
              description "Total number of packets matching a flow";
              type rwt:zero-based-counter64;
          }
          leaf dropped-packets{
              description "Total number of packets dropped";
              type rwt:zero-based-counter64;
          }
          leaf invalid-packets{
              description "Total number of packets dropped";
              type rwt:zero-based-counter64;
          }
          leaf forward-packets{
              description "Total number of packets forwarded";
              type rwt:zero-based-counter64;
          }
          leaf priority-packets{
              description "Total number of high-priority packets (arp..)";
              type rwt:zero-based-counter64;
          }
          leaf kni-tx-packets{
              description "Total number of packets sent to KNI interface in the kernel";
              type rwt:zero-based-counter64;
          }
          leaf rate-limited{
              description "Total number of packets sent to KNI but rate-limited";
              type rwt:zero-based-counter64;
          }
          leaf kni-vf-packets{
              description "Total number of packets sent over vf to the lead";
              type rwt:zero-based-counter64;
          }
          leaf kni-vf-dropped{
              description "Total number of packets sent over vf to the lead dropped";
              type rwt:zero-based-counter64;
          }
          leaf kni-dropped{
              description "Total number of packets sent to kni that are dropped";
              type rwt:zero-based-counter64;
          }
          leaf kni-packets-noring{
              description "Total number of packets sent to KNI but no ring";
              type rwt:zero-based-counter64;
          }
          leaf kni-packets-nobuf{
              description "Total number of packets sent to KNI but no buffer";
              type rwt:zero-based-counter64;
          }
      }
  }
  
  grouping network-packet-counters{
      list fastpath{
          rwpb:field-inline-max yang;
          max-elements 1;
          
          key "instance";
          
          leaf instance {
              type uint32;
              description "Virtual-Fabric Port Identifier";
          }
          container rx{
              uses network-packet-counters-direction;
          }
          container tx{
              uses network-packet-counters-direction;
          }
      }
  }

  grouping kernel-stats{
      container kernel-stats{
          rwpb:msg-new KernelKniStats;
          rwpb:msg-flat true;
          
          list device{
              rwpb:field-inline-max "yang";
              max-elements 128;
              
              key "name";
              leaf name{
                  rwpb:field-string-max 16;
                  type string;  
              }
              leaf ifindex{
                  description "Kernel ifindex of the device\n";
                  type uint32;
              }
              
              leaf rx_packets{
                  description "Number of packets recevied by the kernel from fastpath\n";
                  type uint64;
              }
              
              leaf rx_as_tx_packets{
                  description "Number of packets recevied by the kernel from fastpath in egress direction with respect to fastpath (application->fastpath)\n";
                  type uint64;
              }
              leaf rx_as_tx_filtered{
                  description "Number of packets received by the kernel in egress direction which are dropped (not delivered to kernel network stack)";
                  type uint64;
              }
              leaf rx_as_tx_delivered{
                  description "Number of packets received by the kernel in egress direction which are delivered to kernel network stack)";
                  type uint64;
              }
              leaf rx_only_packets{
                  description "Number of packets received by the kernel from fastpath in ingress direction";
                  type uint64;
              }
              leaf rx_only_filtered{
                  description "Number of packets received by the kernel from fastpath in ingress direction but dropped before delivering to network stack";
                  type uint64;
              }
              leaf rx_only_delivered{
                  description "Number of packets received by the kernel from fastpath in ingress direction delivered to network stack";
                  type uint64;
              }
              leaf rx_dropped{
                  description "Number of packets received by the kernel from fastpath but dropped (lack of skb)";
                  type uint64;
              }
              
              leaf tx_packets{
                  description "Number of packets sent by the kernel to fastpath";
                  type uint64;
              }
              
              leaf tx_dropped{
                  description "Number of packets dropped by the kernel when sending to fastpath";
                  type uint64;
              }
              leaf tx_no_txq{
                  description "Number of packets dropped by kernel due to lack of txq space(slow reader fastpath)";
                  type uint64;
              }
              leaf tx_no_allocq{
                  description "Number of packets dropped by kernel due to lack of allocq";
                  type uint64;
              }
              leaf tx_enq_fail{
                  description "Number of packets dropped by kernel due to enqueue fail";
                  type uint64;
              }
              leaf tx_deq_fail{
                  description "Number of packets dropped by kernel due to dequeue fail";
                  type uint64;
              }
          }
      }
  }
  
  grouping network-context-state{
      list network-context-state {
          config false;
          rwpb:field-inline-max yang;
          rwpb:msg-new NetworkContextState;
          max-elements 32;
          key "name";
          leaf name{
              description "Network context";
              type string;
              rwpb:field-inline "true";
              rwpb:field-string-max 64;
          }
          leaf platform-name{
              description "Network Namespace name";
              type string;
              rwpb:field-inline "true";
              rwpb:field-string-max 64;
          }
          container ipv4 {
              rwpb:msg-new Ipv4Info;
              rwpb:msg-flat true;
              rwpb:msg-proto-max-size "234708";

              uses ip-family;
              list arp{
                  rwpb:msg-new IpArpInfo;
                  rwpb:msg-flat true;
                  
                  rwpb:field-inline-max yang;
                  max-elements 64;
                  
                  key "address";
                  
                  leaf address {
                      description "IPv4 address of the arp entry";
                      type rwt:ipv4-address;
                      rwpb:field-string-max 16;
                  }
                  leaf mac{
                      description "MAC address of the arp entry";
                      type rwt:mac-address;
                      rwpb:field-string-max 18;
                  }
                  leaf lportname{
                      description "Interface of the arp entry";
                      type string;
                      rwpb:field-string-max 64;
                  }
              }      
              list filter{
                  rwpb:msg-new IpFilterInfo;
                  rwpb:msg-flat true;
                  
                  rwpb:field-inline-max yang;
                  max-elements 32;
                  
                  key "inodeid";
                  
                  leaf inodeid {
                      type uint32;
                  }
                  leaf lportname{
                      type string;
                      rwpb:field-string-max 64;
                  }
                  leaf bpflen{
                      type uint32;
                  }
              }
              list acl
              {
                  rwpb:msg-new IpAclInfo;
                  rwpb:msg-flat true;
                  rwpb:field-inline-max yang;
                  max-elements 32;
                  
                  key "name";
                  
                  leaf name {
                      type string;
                      rwpb:field-string-max 64;
                  }
              }
          }
          container ipv6 {
              rwpb:msg-new Ipv6Info;
              rwpb:msg-flat true;
              rwpb:msg-proto-max-size "223236";
              uses ip-family;
              list neigh{
                  rwpb:msg-new IpNeighInfo;
                  rwpb:msg-flat true;
                  
                  rwpb:field-inline-max yang;
                  max-elements 32;
                  
                  key "address";
                  
                  leaf address {
                      description "IPv6 address of the arp entry";
                      type rwt:ipv6-address;
                      rwpb:field-string-max 16;
                  }
                  leaf mac{
                      description "MAC address of the arp entry";
                      type rwt:mac-address;
                      rwpb:field-string-max 18;
                  }
                  leaf lportname{
                      description "Interface Name of the arp entry";
                      type string;
                      rwpb:field-string-max 64;
                  }
              }
          }
          container packet-counters{
              rwpb:msg-new NcPacketCounters;
              rwpb:msg-flat true;
              uses network-packet-counters;
          }
      }
  }
  
  /* ATTN: check rw-base to see if more definitions should be added.

     +-- rw node*[id]
     +-- rw id
     +-- rw trafgen-template
     |   +-- rw (template-type)
     |       +-- : rw (range-template)
     |       |    +-- rw port* [id]
     |       |       +-- rw id
     |       |       +-- rw GROUPING range-param-attr
     |       +-- : rw (sequence-template)
     |       |   +-- rw port* [id]
     |       |       +-- rw id
     |       |       +-- rw sequence* [id]
     |       |           +-- rw id
     |       |           +-- rw GROUPING template-attr
     |       +-- : rw (single-template)
     |       |   +-- rw port* [id]
     |       |       +-- rw id
     |       |       +-- rw GROUPING template-attr
     |       +-- : rw (transmit-params)
     |       |   +-- rw port* [id]
     |       |       +-- rw id
     |       |       +-- rw GROUPING transmit-params
     |       +-- : rw (rx-params)
     |           +-- rw port* [id]
     |           +-- rw id
     |           +-- (...)
     +-- rw port* [name]
     +-- rw name
     +-- rw open
     |   +-- rw ip-fastpat
     |   +-- rw trafgen
     +-- rw receive-q-length
     +-- rw descriptors (...)
     +-- rw flow-control (...)
     +-- rw bind (...)             
  */
  augment /rwbase:node {
      container numa-map {
          rwcli:new-mode "numa-map";
          rwpb:msg-new ConfigNumaMap;
          rwpb:msg-flat "true";
          description "configuration for ethernet port to NUMA mapping";
          
          list port {
              rwpb:field-inline-max yang;
              max-elements 64;
              description "configuration for ethernet port to NUMA mapping";
              
              key "mac-address";
              
              leaf mac-address {
                  type rwt:mac-address;
                  rwpb:field-string-max 18;
                  description "primary mac-address of the port";
              }
              leaf numa-socket {
                  type int32;
                  description "CPU numa socket where the port is attached";
              }
          }
     }
  }
  
  /**
   * RPCs for fast path
   */
  rpc start {
    input {      
      container colony {
        rwpb:msg-new StartTraffic;
        rwpb:msg-flat true;
        rwpb:field-inline "true";
        leaf name {
          rwpb:field-inline "true";
          rwpb:field-string-max 64;
          type string;
        }
        container traffic {
          choice port-range {
            case  all {
              leaf all {
                type empty;
              }
            }
            case  port {
              leaf port-name {
                rwpb:field-inline "true";
                rwpb:field-string-max 64;
                type string;
              }
            }
          }
        }
        container ip-receiver-app {
          leaf name {
             rwpb:field-inline "true";
             rwpb:field-string-max 64;
             type string;
          }
        }
      }
    }
  }
  
  rpc stop {
    input {
      container colony {
        rwpb:msg-new StopTraffic;
        rwpb:msg-flat true;
        rwpb:field-inline "true";
        leaf name {
          rwpb:field-inline "true";
          rwpb:field-string-max 64;
          type string;
        }
        container traffic {
          choice port-range {
            case  all {
              leaf all {
                type empty;
              }
            }
            case  port {
              leaf port-name {
                rwpb:field-inline "true";
                rwpb:field-string-max 64;
                type string;
              }
            }
          }
        }
        container ip-receiver-app {
          leaf name {
             rwpb:field-inline "true";
             rwpb:field-string-max 64;
             type string;
          }
        }                                  
      }
    }
  }

  rpc clear {
    input {
      container colony {
        rwpb:msg-new ClearPort;
        rwpb:msg-flat true;
        rwpb:field-inline "true";
        leaf name {
          rwpb:field-inline "true";
          rwpb:field-string-max 64;
          type string;
        }
        container counters {
          choice port-range {
            case  all {
              leaf all {
                type empty;
              }
            }
            case  port {
              leaf port-name {
                rwpb:field-inline "true";
                rwpb:field-string-max 64;
                type string;
              }
            }
          }
        }
      }      
    }
  }
            
  rpc fpath-debug {
    input {
      container node {      
        rwpb:msg-new FpathDebug;
        rwpb:msg-flat "true";
        rwpb:field-inline "true";

        leaf id {
          type uint32;
        }

        choice operation {
          container show {
            description "Show operation";
            container thread {
              presence true;
              description "Information on thread";
              leaf lcore {
                type uint32;
                description "Core Id";
              }
            } //thread
            leaf work {
              type empty;
              description "Information on work";
            } //thread
            leaf lcore {
              type empty;
              description "Information on lcore";
            } //lcore
            container table {
              presence true;
              description "Information on FastPath related global tables";
              leaf vsapid-vfapid-bindings {
                description "VSAPID to VFAPID bindings";
                type empty;
              }
              leaf vfapid-address-bindings {
                description "VFAPID to Address bindings";
                type empty;
              }
              container fpath-hashbin-bindings {
                presence true;
                description "Fpath instance to hashbins bindings";
                leaf rwfpath-instance {
                  type int32;
                  description "Fpath instance id";
                }
              }
              leaf ip-signature-bindings {
                type empty;
                description "IP Signature Table";
              }
              leaf registered-fpath {
                type empty;
                description "Registered Fpath";
              }
            } // table
          } //show   
          container start {
            description "Start operation";
            container thread {
              leaf lcore {
                type uint32;
                description "Core Id";
              }
            } //thread
            leaf fast-path {
              type empty;
              description "fast path";
            } //fast-path
            leaf hashbin-distribution {
              type empty;
              description "Initiate Hashbin distribution";
            } // hashbin-distribution
          } //start
          container stop {
            container thread {
              description "Stop operation";
              leaf lcore {
                type uint32;
                description "Core Id";
              }
            } //thread
            leaf fast-path {
              type empty;
              description "fast path";
            } //fast-path
          } //stop
          container assign {
            description "Assign operation";             
            leaf work-id {
              type uint32;
              description "Work Id";
            }
            leaf lcore-id {
              type uint32;
              description "lcore-id";
            }          
          } //assign
          container test{
            description "Test operation";
            container rwfpath {
              description "Test operation for RW.Fpath";
              container msg-test{
                description "Messenging test";
                leaf fpctrl-instance {
                  description "RW.Fpath instance";
                  type uint32;
                }
              }
            }
            container rwfpctrl {
              description "Test operation for RW.Fpath";
              container msg-test{
                description "Messenging test";
                leaf fpath-instance {
                  description "RW.Fpath instance";
                  type uint32;
                }
              }
            }
          } // test
        } // choice
      } // node
    } // RPC fath-debug
    
    output {
      rwpb:msg-proto-max-size "1646020";
      container work-info {
        rwpb:msg-new RwWorkInfo;
        rwpb:msg-flat true;
        rwpb:field-inline "true";
        
        list work {
          rwpb:field-inline-max yang;
          max-elements 256;
          
          key "id";
          
          leaf id {
            type uint32;
            description "Id";
          }
          
          leaf name {
            type string;
            rwpb:field-string-max 64;
            description "Work name";
          }
          leaf port-id {
            type rwt:port-number;
            description "Port Id";
          }
          leaf port-name {
           type rwfpath-base-string;
            rwpb:field-string-max 256;
            description "Port Name";
          }
          
          leaf work-instance-id {
            type int32;
            description "Work instance Id";
          }
          leaf lcore-id {
            type int32;
            description "lcore assigned";
          }
        }
      }

      container lcore-info {
        rwpb:msg-new RwLcoreInfo;
        rwpb:msg-flat true;
        rwpb:field-inline "true";
        
        list lcore {
          rwpb:field-inline-max yang;
          max-elements 64;
          
          key "id";
          
          leaf id {
            type uint32;
            description "Id";
          }
          
          leaf socket {
            type int32;
            description "NUMA Socket Id";
          }
          
          leaf core-id {
            type uint32;
            description "Core Id";
          }
          
          leaf thread-status {
            type string;
            rwpb:field-string-max 256;
            description "Thread Status";
          }
          
          leaf thread-type {
            type string;
            rwpb:field-string-max 256;
            description "Thread Type";
          }
          
          leaf tx-q-id {
            type uint32;
            description "Tx Q Id";
          }
          leaf num-works {
            type uint32;
            description "Num works Assigned"; 
          }
        }
      }
      
      container lcore-id-info {
        rwpb:msg-new RwLcoreIdInfo;
        rwpb:msg-flat true;
        rwpb:field-inline "true";
        
        leaf id {
          type uint32;
          description "Id";
        }
        list work {
          rwpb:field-inline-max yang;
          max-elements 32;
          
          key "work-id";
          
          leaf work-id {
            type uint32;
            description "Work Id";
          }
          
          leaf work-name {
            type string;
            rwpb:field-string-max 64;
            description "Work name";
          }
        }
      }
      container lcore_thread-info {
        rwpb:msg-new RwFpDebugLcoreThreadInfo;
        rwpb:msg-flat true;
        rwpb:field-inline "true";
        
        leaf lcore-id {
          type int32;
          description "lcore Id";
        }
        
        leaf thread-type {
          type string;
          rwpb:field-string-max 256;
          description "Thread Type";
        }
        
        leaf tx-q-id {
          type uint32;
          description "Tx Q Id";
        }
        
        list work_queue {
          rwpb:field-inline-max yang;
          max-elements 128; // TBD
          
          key "work_id";
          
          leaf work_id {
            type uint32;
            description "Work instance Id";
          }
          leaf work_name {
            type string;
            rwpb:field-string-max 64;
            description "Work name";
          }
          leaf work_flag {
            type uint16;
            description "bitmap flag for work property";
          }
          leaf work_metric {
            type uint64;
            description "work accomplished so far";
          }
          leaf work_metric_checkpoint {
            type uint64;
            description "work accomplished last snapshot";
          }
          leaf work_cont_low {
            type uint16;
            description "Number conscecute low work cycles";
          }
        } //Work Info

        list app-data {
          rwpb:field-inline-max yang;
          max-elements 4;

          key "app_id";

          leaf app_id {
            type uint32;
            description "Channel Application Id";
          }
        
          list channel-stats {
            rwpb:field-inline-max yang;
            max-elements 32;

            key "channel_id";

            leaf channel_id {
              type uint32;
              description "Channel Id";
            }
        
           leaf total-transmit {
              type uint64;
              description "Total transmitted packets";
            }

           leaf total-dropped {
              type uint64;
              description "Total dropped packets";
            }
          }
        }
      } // thread-info
      container vsapid-table {
        rwpb:msg-new RwFpVsapidTable;
        rwpb:msg-flat true;
        rwpb:field-inline "true";

        list vsapid-to-vfapid {
          rwpb:field-inline-max yang;
          max-elements 1024; 

          key "vsapid";
          leaf vsapid {
            type int32;
            description "Virtual Service Access Point ID";
          }
          leaf fpath {
            type int32;
            description "Fpath Instance";
          }
          leaf groupid {
            type int32;
            description "Resource Group ID";
          }
          leaf vfapid {
            description "Virtual Fabric Access Port ID";
            type int32;
          }  
        } // vsapid-to-vfapid list
      }
      container vfapid-table {
        rwpb:msg-new RwFpVfapidTable;
        rwpb:msg-flat true;
        rwpb:field-inline "true";

        list vfapid-to-addr {
          rwpb:field-inline-max yang;
          max-elements 1024; 

          key "vfapid";

          leaf vfapid {
            type int32;
            description "Virtual Fabric Access Port ID";
          }
          leaf groupid {
            type uint32;
            description "Group id";
          }
          leaf fpath {
            type int32;
            description "Fpath Instance";
          }
          leaf ncid {
            type int32;
            description "Network Context ID";
          }
          leaf ip_address {
            type rwt:ip-address;
            rwpb:field-string-max 46;
            description "IP Address where VFAPID is accessible";
          }
          leaf port {
            type int32;
            description "UDP port where VFAPID is accessible";
          }
        }
      } // vfapid-table
      container hashbin-table {
        rwpb:msg-new RwFpHashbinTable;
        rwpb:msg-flat true;
        rwpb:field-inline "true";

        leaf fpath_hashbin_credits {
          type uint32;
          description "RW.Fpath hashbin credits";
        }

        leaf total_hashbin_credits {
          type uint32;
          description "Cumulative hashbin credits";
        }

        leaf total_hashbins_assigned {
          type uint32;
          description "Total hashbins assigned to this RW.Fpath Instance";
        }
        
        list hashbins {
          rwpb:field-inline-max yang;
          max-elements 100; 
            
          container hashbin-range {
            leaf hashbin-start{
              type int32;
              description "Hashbin Range Start";
            }
            leaf hashbin-end {
              type int32;
              description "Hashbin Range End";
            }            
          }
        } // hashbins
      } // hashbin-table
      container ip-signature-table {
        rwpb:msg-new RwFpIpsigTable;
        rwpb:msg-flat true;
        rwpb:msg-proto-max-size "1168424";
        rwpb:field-inline "true";
        list ip-signature {
          rwpb:field-inline-max yang;
          max-elements 100; 

          key "sig-id";

          leaf sig-id {
            description "Signature ID";
            type uint32;
          }
          leaf flow-type {
            description "Flow Type";
            type uint32;
          }
          leaf ncid {
            description "Network Context ID";
            type uint32;
          }
          leaf ip-address {
            description "IP Address";
            type rwt:ip-address;
            rwpb:field-string-max 46;
          }
          
          leaf sig-mask {
            description "Signature Mask";
            type string;
            rwpb:field-string-max 512;
          }
          leaf sig-key {
            description "Signature Key";
            type string;
            rwpb:field-string-max 512;
          }
        }
      } // IP Signature Table
      container registered-fpath {
        rwpb:msg-new RwFpFpath;
        rwpb:msg-flat true;
        rwpb:field-inline "true";
        leaf Fpctrl-id {
          type uint32;
          description "Fpctrl instance";
        }
        
        list fpath {
          rwpb:field-inline-max yang;
          max-elements 1024; 
          key "fpath-id";
          leaf fpath-id {
            type uint32;
            description "Fpath ID";
          }
        }
      } // registered-fpath
    } // output
  } // fpath_debug
  
  container return_status {
    rwpb:msg-flat true;
    rwpb:field-inline "true";
    config "false";
    
    leaf error_number {
      type int32;
      description "Error number";
    }
    leaf error_string {
      type string;
      rwpb:field-string-max 128;
      description "Error string value";
    }
  }     

} // module rw-fpath
