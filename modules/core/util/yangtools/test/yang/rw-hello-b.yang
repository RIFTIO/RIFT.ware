/*
 * STANDARD_RIFT_IO_COPYRIGHT
 *
 */

// Configuration references

module rw-hello-b
{
  namespace "http://riftio.com/ns/riftware-1.0/rw-hello";
  prefix "rwhello";

  //import ietf-inet-types {
  //  prefix inet;
  //} 

  //import rw-base-b {
  //  prefix rwbase;
  //}

  import rw-pb-ext {
    prefix "rwpb";
  }

  grouping rwhello-service {
    list rwhello-service {
      rwpb:msg-new ConfigHelloWorld;
      rwpb:msg-flat true;

      key name;
      leaf name {
        rwpb:field-string-max 64;
        type string;
      }

      leaf output-message {
        rwpb:field-string-max 64;
        type string;
      }
      leaf statistics {
        config false;
          description "Number of commands entered";
          type int32;
      }
      
      container commands {
        config false;
        leaf-list output-messages {
          description "All commands entered";
          rwpb:field-inline-max 20;

          type string;
          rwpb:field-string-max 64;          
        }        
      }
    }
  } // grouping ipsec-service
  
  rpc log {
    input {
      rwpb:msg-new SetLogLevel;
      rwpb:msg-flat true;

      leaf set-level {
        type int8;
        description "Set the logging level";
      }
    }
    output {
      leaf level {
        type int8;
        description "Current Level";
      }
    }
  }
} // module rw-hello
