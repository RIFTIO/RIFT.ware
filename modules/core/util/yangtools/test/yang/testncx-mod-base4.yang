/* STANDARD_RIFT_IO_COPYRIGHT */

/**
 * @file testncx-mod-base4.yang
 * @author Tom Seidenberg
 * @date 2014/03/25
 * @brief yangncx test file for modules
 */

module testncx-mod-base4
{
  namespace "http://riftio.com/ns/core/util/yangtools/tests/testncx-mod-base4";
  prefix "tnmb4";
  description "Module testing for yangncx.";
  revision 2014-03-25 { description "Initial version"; }

  /////////////////////////////////////////////////////////////////////////////
  typedef b4t1 {
    type int32;
    description "A typedef from base4";
  }

  /////////////////////////////////////////////////////////////////////////////
  grouping b4g1 {
    leaf b4g1-b4t1 {
      description "A type b4t1 from group b4g1 in base4";
      type b4t1;
    }

    leaf b4g1-n1 {
      description "A number from group b4g1 in base4";
      type int64;
    }

    leaf b4g1-s1 {
      description "A string from group b4g1 in base4";
      type string;
    }
  }

  /////////////////////////////////////////////////////////////////////////////
  container b4c1 {
    leaf b4c1-b4t1 {
      description "A type b4t1 from container b4c1 in base4";
      type b4t1;
    }

    leaf b4c1-n1 {
      description "A number from container b4c1 in base4";
      type int64;
    }

    leaf b4c1-s1 {
      description "A string from container b4c1 in base4";
      type string;
    }
  }

  /////////////////////////////////////////////////////////////////////////////
  container b4c2 {
    uses b4g1;
  }
}
