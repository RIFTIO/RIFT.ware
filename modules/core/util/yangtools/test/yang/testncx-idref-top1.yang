/* STANDARD_RIFT_IO_COPYRIGHT */

/**
 * @file testncx-idref-top1.yang
 * @author Rajesh Velandy
 * @date 2014/04/03
 * @brief yangncx test file for Identity References
 */

module testncx-idref-top1
{
  namespace "http://riftio.com/ns/core/util/yangtools/tests/testncx-idref-top1";
  prefix "tnx-id-top1";

  import testncx-idref-base1 { prefix "tnx-id-base1"; }  // Give it a different prefix
  import testncx-idref-base2 { prefix "tnx-id-base2"; }  // Give it a different prefix

  description "Module testing for yangncxi Idref";
  revision 2014-04-03 { description "Initial version"; }

  identity french {
    base tnx-id-base1:language;
    description "The Language French";
  }

  identity german {
    base tnx-id-base1:language;
    description "The Language German";
  }

  leaf language-name {
    type identityref {
      base "tnx-id-base1:language"; 
    }
  }
}
