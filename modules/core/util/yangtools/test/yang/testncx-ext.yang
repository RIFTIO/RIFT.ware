/* STANDARD_RIFT_IO_COPYRIGHT */

/**
 * @file testncx-ext.yang
 * @author Tom Seidenberg
 * @date 2014/03/26
 * @brief yangncx test file for extensions
 */

module testncx-ext
{
  namespace "http://riftio.com/ns/core/util/yangtools/tests/testncx-ext";
  prefix "tnext";
  description "Test extension support in libncx";
  revision 2014-03-20 { description "Initial version"; }

  extension ext-a {
    description "extension a";
  }

  extension ext-b {
    description "extension b";
    reference "not a good reference";
    argument "b-arg";
  }

  extension ext-1 {
    description "extension 1";
    argument "arg1";
  }

  tnext:ext-a;
  tnext:ext-b "module-level b value";
  tnext:ext-1 "first module-level ext-1 value";
  tnext:ext-1 "second module-level ext-1 value";

  identity id {
    description "Test identity";
    tnext:ext-a;
    tnext:ext-b "id identity extension";
  }

  identity new-id {
    base id;
    description "Derived identity";
    tnext:ext-b "new-id identity extension";
    tnext:ext-1 "new-id only extension";
  }

  // typedef
  // augment

  grouping a-group {
    tnext:ext-1 "ext 1 in a-group";
    container cina {
      description "c in a-group";
      tnext:ext-1 "ext 1 in a-group:cina";
      leaf lf1 {
        type string;
      }
      leaf lf2 {
        type string;
      }
    }
    leaf lina {
      description "leaf in a-group";
      tnext:ext-1 "ext 1 in a-group:lina";
      tnext:ext-b "ext b in a-group:lina";
      type string;
    }
    leaf lf5 {
      type string;
    }
  }

  grouping b-group {
    leaf lf8 {
      type string;
    }
  }

  container top1 {
    tnext:ext-1 "ext 1 in top1";
    uses a-group {
      tnext:ext-a;
    }
    container cint1 {
      description "cont in top1";
      tnext:ext-1 "ext 1 in cint1";
      leaf lf1 {
        tnext:ext-b "ext b in lf1, not group-a";
        type string;
      }
    }
    leaf lf6 {
      type string;
    }
    leaf lf7 {
      type string;
      tnext:ext-1 "ext 1 in lf7";
      tnext:ext-b "ext b in lf7";
    }
  }

  container top2 {
    tnext:ext-b "ext b in top2";
    uses a-group {
      tnext:ext-1 "ext 1 in top2's uses";
      tnext:ext-b "ext b in top2's uses";
    }
  }

  container top3 {
    uses b-group {
      tnext:ext-a;
    }
  }
}
