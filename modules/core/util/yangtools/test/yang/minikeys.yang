/*
 * STANDARD_RIFT_IO_COPYRIGHT
 *
 */

module minikeys
{
  namespace "http://riftio.com/ns/core/util/yangtools/tests/minikeys";
  prefix "minikeys";

  import rw-pb-ext { prefix "rwpb"; }

  description "This YANG module creates different types of minikeys";
  revision 2014-05-27 {
    description "Initial version"; }

  container  company {

    list mk-string {
      key "name";
      leaf name {
        description "Name of the company";
        type string;
      }
    }

    list mk-int {
      key "id";

      leaf id {
        description "Employee Id";
        type int32;
      }
    }

    list mk-int64 {
      key "f1";

      leaf f1 {
        description "int64 key";
        type int64;
      }
    }

    list mk-strinl {
      key "s1";

      leaf s1 {
        description "String Key";
        type string;
        rwpb:field-string-max 50;
        rwpb:field-inline "true";
      }
    }
  }

  list multi-keys {
    key "ml k2 k3";

    leaf ml {
       description "Key1";
       type int32;
    }

    leaf k2 {
      description "Key2";
      type string;
      rwpb:field-string-max 50;
    }

    leaf k3 {
      description "Key3";
      type uint64;
    }
  }
}
