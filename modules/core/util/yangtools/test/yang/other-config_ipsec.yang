/*
 * STANDARD_RIFT_IO_COPYRIGHT
 *
 */

// Configuration references
//
// Cisco: Cisco ASA configuration guide/Cisco IOS XML 12.4T Configuring Secruity for VPNs
// Juniper: JunOS 10.0 security CLI reference
// Strongswan: http://wiki.strongswan.org/projects/strongswan/wiki/ConnSection
// Vyatta: Vyatta VPN reference guide

module other-config_ipsec
{
  namespace "http://riftio.com/ns/riftware-1.0/other-config_ipsec";
  prefix "config_ipsec";

  import ietf-inet-types {prefix inet; }
  import other-config_base { prefix config; }

  description "IPsec related configuration";
  revision 2014-05-27 {
    description "Initial version"; 
  }

  grouping ikesa-proposal {
    list ikesa-proposal {
      key name;
      leaf name {
        type string;
      }
      leaf authentication-algorithm {
        // Cisco supports:
        //   crypto isakmp policy hash (md5 | sha)
        //
        // Juniper supports:
        //   authentication-algorithm (md5 | sha1| sha-256)
        //   
        // StrongSwan supports:
        //   ike = <encryption-integrity-dhgroup>
        //   where <integrity> can be one of the following:
        //     md5 md5_128 sha1 sha1_160 aesxcbc sha2_256 sha2_384 sha2_512 sha2_256_96
        //
        // Vyatta supports:
        //   set vpn ipsec ike-group <name> proposal <num> hash (md5 | sha1)
        type enumeration {
          enum md5;
          enum sha1;
          enum sha-256;
        }
      }
      leaf dh-group {
        // Cisco supports:
        //   crypto isakmp policy group (1 | 2 | 5)
        //
        // Juniper supports:
        //   dh-group (group1 | group2 | group5)
        //
        // StrongSwan supports:
        //   ike = <encryption-integrity-dhgroup>
        //   where <dhgroup> can be one of the following:
        //   Modulo Prime Groups (modp68 modp1024 modp1536 modp2048 modp3072 modp4096 modp6144 modp8192)
        //   Modulo Prime Groups with Prime Order Subgroup (modp1024s160 modp2048s224 modp2048s256)
        //   Elliptic Curve Groups (ecp192 ecp224 ecp256 ecp384 ecp521)
        //
        // Vayatta supports:
        //   set vpn ipsec ike-group <name> proposal <num> dh-group (2 | 5 )
        type enumeration {
          enum group1;
          enum group2;
          enum group5;
        }
      }

      leaf encryption-algorithm {
        // Cisco supports:
        //   crypto isakmp policy encryption (des | 3des | aes | aes-192 | aes-256)
        //
        // Juniper supports:
        //   encryption-algorithm (des-cbc | 3des-cbc | aes-128-cbc | aes-192-cbc | aes-256-cbc)
        //
        // StrongSwan supports:
        //   ike = <encryption-integrity-dhgroup>
        //   where <encryption> can be one of the following:
        //     3des cast128 blowfish128 blowfish192 blowfish256 null
        //     aes128 aes192 aes256 aes128ctr aes192ctr aes256ctr
        //     aes128ccm8 aes192ccm8 aes256ccm8 aes128ccm12 aes192ccm12 aes256ccm12
        //     aes128ccm16 aes192ccm16 aes256ccm16 aes128gcm8 aes192gcm8 aes256gcm8
        //     aes128gcm12 aes192gcm12 aes256gcm12 aes128gcm16 aes192gcm16 aes256gcm16
        //     aes128gmac aes192gmac aes256gmac
        //     camellia128 camellia192 camellia256 camellia128ctr camellia192ctr camellia256ctr
        //     camellia128ccm8 camellia192ccm8 camellia256ccm8 camellia128ccm12 camellia192ccm12
        //     camellia256ccm12 camellia128ccm16 camellia192ccm16 camellia256ccm16
        //
        // Vayatta supports:
        //   set vpn ipsec ike-group <name> proposal <num> encryption (aes128 | aes256 | 3des)
        type enumeration {
          enum des-cbc;
          enum 3des-cbc;
          enum aes-128-cbc;
          enum aes-192-cbc;
          enum aes-256-cbc;
        }
      }
      leaf prf {
        // Cisco supports:
        //   Not supported (same as integrity)
        //
        // Juniper supports:
        //   Not supported (same as integrity)
        //
        // StrongSwan supports:
        //   ike = <encryption-integrity[-prf]-dhgroup>
        //   where <prf> can be any integrity altgorithm
        //
        // Vayatta supports:
        //   Not supported (same as integrity)
        type enumeration {
          enum prf-md5;
          enum prf-sha1;
          enum prf-sha-256;
        }
      }
    }
  } // grouping ike-proposal

  grouping ipsecsa-proposal {
    list ipsecsa-proposal {
      key name;
      leaf name {
        type string;
      }
      leaf authentication-algorithm {
        // Cisco supports:
        //   crypto ipsec transform-set <name> (... transforms ...) (for IKEv1)
        //   crypto ikev2 proposal proposal-name integrity (sha | md5) (for IKEv2)
        //
        // Juniper supports:
        //   authentication-algorithm (md5 | sha1| sha-256)
        //   
        // StrongSwan supports:
        //   esp = <encryption-integrity[-dhgroup][-esnmode]>
        //   where <integrity> can be one of the following:
        //     md5 md5_128 sha1 sha1_160 aesxcbc sha2_256 sha2_384 sha2_512 sha2_256_96
        //
        // Vyatta supports:
        //   set vpn ipsec esp-group <name> proposal <num> hash (md5 | sha1)
        type enumeration {
          enum md5;
          enum sha1;
          enum sha-256;
        }
      }
      leaf compression {
        // Cisco supports:
        //   crypto ipsec transform-set <name> comp-lzs
        //
        // Juniper supports:
        //   Not supported
        //
        // StrongSwan supports:
        //   compress = yes | no
        //
        // Vayatta supports:
        //   set vpn ipsec esp-group <name> compression (enable | disable)
        type enumeration {
          enum disable;
          enum comp-lzs;
        }
      }
      leaf dh-group {
        // Cisco supports:
        //   crypto map <name> <seq> set pfs (group1 | group2 | group5])
        //   crypto ikev2 proposal proposal-name group (group1 | group2 | group5) (for IKEv2)
        //
        // Juniper supports:
        //   dh-group (group1 | group2 | group5)
        //
        // StrongSwan supports:
        //   ike = <encryption-integrity-dhgroup>
        //   where <dhgroup> can be one of the following:
        //   Modulo Prime Groups (modp68 modp1024 modp1536 modp2048 modp3072 modp4096 modp6144 modp8192)
        //   Modulo Prime Groups with Prime Order Subgroup (modp1024s160 modp2048s224 modp2048s256)
        //   Elliptic Curve Groups (ecp192 ecp224 ecp256 ecp384 ecp521)
        //
        // Vayatta supports:
        //   set vpn ipsec esp-group <name> pfs (enable | dh-group2 | dh-group5 | disable)
        type enumeration {
          enum group1;
          enum group2;
          enum group5;
        }
      }
      leaf encryption-algorithm {
        // Cisco supports:
        //   crypto ipsec transform-set <name> <transforms> (for ikev1)
        //   crypto ikev2 proposal proposal-name encryption <transforms> (for IKEv2)
        //   where <transforms> can be one of the following:
        //     ah-md5-hmac ah-sha-hmac esp-aes esp-gcm esp-gmac esp-gcm esp-gmac esp-aes 192 esp-aes 256
        //     esp-des esp-3des esp-null esp-seal esp-md5-hmac esp-sha-hmac comp-lzs
        //
        // Juniper supports:
        //   encryption-algorithm (des-cbc | 3des-cbc | aes-128-cbc | aes-192-cbc | aes-256-cbc)
        //
        // StrongSwan supports:
        //   esp = <encryption-integrity[-dhgroup][-esnmode]>
        //   where <encryption> can be one of the following:
        //     3des cast128 blowfish128 blowfish192 blowfish256 null
        //     aes128 aes192 aes256 aes128ctr aes192ctr aes256ctr
        //     aes128ccm8 aes192ccm8 aes256ccm8 aes128ccm12 aes192ccm12 aes256ccm12
        //     aes128ccm16 aes192ccm16 aes256ccm16 aes128gcm8 aes192gcm8 aes256gcm8
        //     aes128gcm12 aes192gcm12 aes256gcm12 aes128gcm16 aes192gcm16 aes256gcm16
        //     aes128gmac aes192gmac aes256gmac
        //     camellia128 camellia192 camellia256 camellia128ctr camellia192ctr camellia256ctr
        //     camellia128ccm8 camellia192ccm8 camellia256ccm8 camellia128ccm12 camellia192ccm12
        //     camellia256ccm12 camellia128ccm16 camellia192ccm16 camellia256ccm16
        //
        // Vayatta supports:
        //   set vpn ipsec esp-group <name> proposal <num> encryption (aes128 | aes256 | 3des)
        type enumeration {
          enum des-cbc;
          enum 3des-cbc;
          enum aes-128-cbc;
          enum aes-192-cbc;
          enum aes-256-cbc;
        }
      }
      leaf esn-mode {
        // Cisco supports:
        //   Not supported
        //
        // Juniper supports:
        //   Not supported
        //
        // StrongSwan supports:
        //   esp = <encryption-integrity[-dhgroup][-esnmode]>
        //   where esnmode is (esn | noesn)
        //
        // Vayatta supports:
        //   set vpn ipsec esp-group <name> proposal <num> encryption (aes128 | aes256 | 3des)
        type enumeration {
          enum esn-off;
          enum esn-on;
        }
      }
    }
  } // grouping ipsec-proposal

  grouping ikesa-params {
    container ikesa-params {
      container lifetime {
        leaf seconds {
          // Cisco supports:
          //   crypto isakmp policy lifetime <seconds>
          //
          // Juniper supports:
          //   lifetime-seconds <seconds>
          //
          // StrongSwan supports:
          //   ikelifetime = <time>
          //
          // Vayatta supports:
          //   set vpn ipsec ike-group <name> lifetime <seconds>
          type int32;
        }
      }
      leaf local-identity {
        // Cisco supports:
        //   crypto isakmp identity {address | hostname | key-id id-string | auto}
        //
        // Juniper supports:
        //  local-identity (distinguished-name string | hostname hostname | inet ipv4-ip-address |
        //                  user-at-hostname e-mail-address )
        //
        // StrongSwan supports:
        //   left|rightid = <id> where id can be:
        //     IP address, a fully-qualified domain name, an email address, or a keyid
        //     fully-qualified domain names can be preceded by an @ to avoid being resolved
        //
        // Vayatta supports:
        //   set vpn ipsec site-to-site peer <peer> authentication id <id>
        type string;
      }
      leaf remote-identity {
        // Cisco supports:
        //
        // Juniper supports:
        //
        // StrongSwan supports:
        //   left|rightid = <id> where id can be:
        //     IP address, a fully-qualified domain name, an email address, or a keyid
        //     fully-qualified domain names can be preceded by an @ to avoid being resolved
        //
        // Vayatta supports:
        // set vpn ipsec site-to-site peer <peer> authentication remote-id <id>
        type string;
      }
      list proposal-list {
        key value;
        leaf value {
          type string;
          // TODO
          // type leafref {
          //   path "/config/service-realm/service/ipsec-network/ikesa-proposal/name";
          // }
        }
      }
    }
  } // grouping ikesa-params

  grouping ipsecsa-params {
    container ipsecsa-params {
      container lifetime {
        container seconds {
          leaf hard-value {
            // Cisco supports:
            //   crypto dynamic-map <name> <seq> set security-association lifetime seconds <seconds>
            //
            // Juniper supports:
            //   lifetime-seconds <seconds>
            //
            // StrongSwan supports:
            //   lifetime = 1h | <time>
            //
            // Vayatta supports:
            //   set vpn ipsec esp-group <name> lifetime <seconds>
            type int32;
          }
          leaf soft-margin {
            // Cisco supports:
            //   Not supported
            //
            // Juniper supports:
            //   Not configurable, defaults to 135/90 seconds for initiator/responder
            //
            // StrongSwan supports:
            //   margintime = <time>
            //
            // Vayatta supports:
            //   Not supported
            type int32;
          }
        }
        container kilobytes {
          leaf hard-value {
            // Cisco supports:
            //   crypto dynamic-map <name> <seq> set security-association lifetime kilobytes <kb>
            //
            // Juniper supports:
            //   lifetime-kilobytes <seconds>
            //
            // StrongSwan supports:
            //   lifebytes = <number>
            //
            // Vayatta supports:
            //   Not supported
            type int32;
          }
          leaf soft-margin {
            // Cisco supports:
            //   Not supported
            //
            // Juniper supports:
            //   Not Supported
            //
            // StrongSwan supports:
            //   marginbytes = <number>
            //
            // Vayatta supports:
            //   Not supported
            type int32;
          }
        }
        container packets {
          leaf hard-value {
            // Cisco supports:
            //   Not supported
            //
            // Juniper supports:
            //   Not supported
            //
            // StrongSwan supports:
            //   lifepackets = <number>
            //
            // Vayatta supports:
            //   Not supported
            type int32;
          }
          leaf soft-margin {
            // Cisco supports:
            //   Not supported
            //
            // Juniper supports:
            //   Not supported
            //
            // StrongSwan supports:
            //   marginpackets = <number>
            //
            // Vayatta supports:
            //   Not supported
            type int32;
          }
        }
      }
      list proposal-list {
        key value;
        leaf value {
          type string;
          // TODO
          // type leafref {
          //  path "/config/service-realm/service/ipsec-network/ipsecsa-proposal/name";
          // }
        }
      }
    }
  } // grouping ikesa-params

  grouping ike-protocol {
    container ike-protocol {
      choice ike-protocol {
        case ikev1 {
          container ikev1 {
            leaf aggressive-mode {
              // Cisco supports:
              //   crypto isakmp am-disable
              //
              // Juniper supports:
              //   mode (aggressive | main)
              //
              // StrongSwan supports:
              //   aggressive = yes | no
              //
              // Vayatta supports:
              //   Not supported
              type boolean;
            }
          }
        }
        case ikev2 {
          container ikev2 {
            //leaf ikev2 {
            //  type empty;
            //}
          }
        }
      }
    }
  } // grouping ike-protocol

  grouping dpd {
    // Cisco supports:
    //    crypto ikev2 dpd interval retry-interval {on-demand | periodic}
    //
    // Juniper supports:
    // dead-peer-detection { always-send; interval seconds; threshold number; }
    //   
    // StrongSwan supports:
    //   dpdaction = none | clear | hold | restart
    //   dpddelay = 30s | <time>
    //   dpdtimeout = 150s | <time>
    //
    // Vayatta supports:
    //    set vpn ipsec ike-group <name> dead-peer-detection
    //      [action (hold | clear | restart) | interval <seconds> | timeout <seconds> ]	
    container dpd {
      leaf disable {
        type empty;
      }
      leaf enable {
        type empty;
      }
      leaf action {
        type enumeration {
          enum clear;
          enum hold;
          enum restart;
        }
      }
      leaf interval {
        type int32;
      }
      leaf originate {
        type enumeration {
          enum on-demand;
          enum periodic;
        }
      }
      leaf timeout {
        type int32;
      }      
    }
  } // grouping dpd

  grouping ike-retransmit {
    leaf ike-retransmit {
      // Cisco supports:
      //   Not supported
      // 
      // Juniper supports:
      //   Not supported
      //
      // StrongSwan supports:
      //   keyingtries = <number> | %forever
      //
      // Vayatta supports:
      //   Not supported
      type int32;
    }
  } // grouping ike-retransmit

  grouping local-tunnel-address {
    leaf local-tunnel-address {
      // Cisco supports:
      //   crypto map map-name local-address interface-id 
      //
      // Juniper supports:
      //   local-gateway address
      //
      // StrongSwan supports:
      //   left|right = <ip address> | <fqdn> | %any
      //
      // Vayatta supports:
      //   set vpn ipsec site-to-site peer <peer> local-address <address>
      type inet:ip-address;
    }
  } // grouping local-tunnel-address

  grouping remote-tunnel-address {
    leaf remote-tunnel-address {
      // Cisco supports:
      //   set peer (hostname | ip-address)
      //
      // Juniper supports:
      //   remote-gateway address
      //
      // StrongSwan supports:
      //   left|right = <ip address> | <fqdn> | %any
      //
      // Vayatta supports:
      //   set vpn ipsec site-to-site peer <peer>
      type inet:ip-address;
    }
  } // grouping remote-tunnel-address

  grouping ike-udp-port {
    leaf local-ike-udp-port {
      // Cisco supports:
      //   Hardcoded to 500
      //
      // Juniper supports:
      //   Hardcoded to 500
      //
      // StrongSwan supports:
      //   left|right = <ip address> | <fqdn> | %any
      //
      // Vayatta supports:
      //   Not supported
      type int32;
    }
    leaf remote-ike-udp-port {
      // Cisco supports:
      //   Hardcoded to 500
      //
      // Juniper supports:
      //   Hardcoded to 500
      //
      // StrongSwan supports:
      //   left|right = <ip address> | <fqdn> | %any
      //
      // Vayatta supports:
      //   Not supported
      type int32;
    }

  } // grouping ike-udp-port

  grouping ipsec-mode-g {
    leaf ipsec-mode {
      // Cisco supports:
      //   crypto ipsec transform-set <name> mode (tunnel | transport)
      //
      // Juniper supports:
      //   mode (transport | tunnel)
      //
      // StrongSwan supports:
      //   type = tunnel | transport | transport_proxy | passthrough | drop
      //
      // Vayatta supports:
      //   set vpn ipsec esp-group <name> mode (tunnel | transport)
      type enumeration {
        enum transport;
        enum tunnel;
      }
    }
  } // grouping ipsec-mode-g

  grouping payload {
    // Cisco supports:
    //   access-list <number> (deny | permit) <protocol> source <source-wild> destination <dest-wild> [log]
    //
    // Juniper supports:
    //   match-direction (input | output)
    //   source-address address
    //   destination-address <address>
    //   protocol/port ranges are not supported
    //
    // StrongSwan supports:
    //   left|rightprotoport = <protocol>/<port>
    //   leftsourceip = %config4 | %config6 | <ip address> (for dynamic addresses)
    //   rightsourceip = %config | <network>/<netmask> | %poolname (for dynamic addresses)
    //   left|rightsubnet = <ip subnet> (for static addresses)
    //
    // Vayatta supports:
    //   set vpn ipsec site-to-site peer <peer> tunnel <tunnel> protocol <protocol>
    //   set vpn ipsec site-to-site peer <peer> tunnel <tunnel> local (port <port> | prefix <prefix>)
    //   set vpn ipsec site-to-site peer <peer> tunnel <tunnel> remote (port <port> | prefix <prefix>)
    list payload {
      key name;
      leaf name {
        type string;
      }
      choice payload-type {
        case static {
/*
ATTN: yangpbc doesn't like this as part of an augment
          choice protocol {
            case tcp {
              leaf tcp {
                type empty;
              }
            }
            case udp {
              leaf udp {
                type empty;
              }
            }
          }
*/
          leaf port {
            type inet:port-number;
          }
          leaf local-subnet {
            type inet:ip-prefix;
          }
          leaf remote-subnet {
            type inet:ip-prefix;
          }
        }
        case dynamic {
        }
      }
    }
  } // grouping payload

  grouping tunnel-policy {
    list tunnel-policy {
      key name;
      leaf name {
        type string;
      }
      uses dpd;
      uses ike-protocol;
      uses ike-retransmit;
      uses ike-udp-port;
      uses ikesa-params;
      uses ipsecsa-params;
      uses ipsec-mode-g;
      uses local-tunnel-address;
      uses payload;
      uses remote-tunnel-address;
    }
  } // grouping tunnel-policy

  grouping ipsec-service {
    list ipsec-network {
      key name;
      leaf name {
        type string;
      }
      uses ikesa-proposal;
      uses ipsecsa-proposal;
      uses tunnel-policy;
    }
  } // grouping ipsec-service

  augment /config:config/config:service-realm {
    container service {
      uses ipsec-service;
    }
  }

  augment /config:show {
    container ipsec {
      container ikesalist {
      }
      container configlist {
      }
    }
  }

  augment /config:clear {
    container ipsec {
      container ikesa {
        leaf id {
          type int32;
        }
      }
      container childsa {
        leaf id {
          type int32;
        }
      }
    }
  }
    
  augment /config:start {
    container ipsec {
      container ikesa {
        leaf name {
          type string;
        }
      }
      container childsa {
        leaf name {
          type string;
        }
      }
    }
  }
} // module other-config_ipsec
