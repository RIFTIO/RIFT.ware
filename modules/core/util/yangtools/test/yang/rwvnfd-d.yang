/*
 * STANDARD_RIFT_IO_COPYRIGHT
 *
 */

module rwvnfd-d
{
  namespace "http://riftio.com/ns/riftware-1.0/rwvnfd";
  prefix "rwvnfd-d";

  import rw-manifest-d {
    prefix "rwmani";
  }

  import rwpaas-vdus-d {
    prefix "rwvdus";
  }

  import rw-pb-ext {
    prefix "rwpb";
  }

  import rw-yang-types {
    prefix rwt;
  }

  import rw-cli-ext {
    prefix "rwcli";
  }

  import ietf-inet-types {
    prefix "inet";
  }

  import rwmano-types-d {
    prefix "rwmanotypes";
  }

  import ietf-yang-types {
    prefix "yang";
  }

  revision 2014-10-27 {
    description
      "Initial revision. This YANG file defines 
       the Virtual Network Function (VNF)";
    reference
      "Derived from earlier versions of base YANG files";
  }

  container vnfd {
    description
        "Virtual Network Function Descriptor.";

    leaf name {
      description "VNF descriptor name.";
      type string;
    }

    leaf vnfd-id {
      description "UUID of the VNF descriptor.";
      type yang:uuid;
    }

    leaf provider {
      description "Vendor name.";
      type string;
    }

    leaf description {
      description "Description of the VNF.";
      type string;
    }

    leaf version {
      description "Version";
      type string;
    }

    list internal-connection-points {
      description
          "List for internal connection points. Each VNFC has zero or more internal
           connection points. Internal connection points are used for connecting 
           the VNF components internal to the VNF. If a VNF has only one VNFC, it
           may not have any internal connection points.";

      key "id";
      leaf id {
        description
            "Identifier for the internal connection points";
        type uint32;
      }

      leaf cp-type {
        description
            "Type of the connection point.";
        type rwmanotypes:connection-point-type;
      }
    }

    list internal-vlds {
      description
          "List of Internal Virtual Link Descriptors (VLD). The internal VLD 
           describes the basic topology of the connectivity (e.g. E-LAN, E-Line, E-Tree) 
           between internal VNF components of the system.";

      key "id";
      leaf id {
        description
            "Identifier for the VLD";
        type uint32;
      }
      leaf vld-type {
        type rwmanotypes:virtual-link-type;
      }

      list internal-connection-points {
        key id;
        leaf id {
          type leafref {
            path "../../../internal-connection-points/id";
          }
        }
      }  
    }

    list connection-points {
      description
          "List for external connection points. Each VNF has one or more external
           connection points. As the name implies that external connection points 
           are used for connecting the VNF to other VNFs or to external networks.
           Each VNF exposes these connection points to the orchestrator. The 
           orchestrator can construct network services by connecting the
           connection points between different VNFs. The NFVO will use VLDs and 
           VNFFGs at the network service level to construct network services.";

      key "id";
      leaf id {
        description
            "Identifier for the external connection points";
        type uint32;
      }

      leaf cp-type {
        description
            "Type of the connection point.";
        type rwmanotypes:connection-point-type;
      }
    }

    list monitoring-params {
      description
          "List parameters to monitor for the VNF. Examples include
           total number of sessions etc.";
      key name;
      leaf name {
        description
            "Name of the parameter to monitor.";
        type string;
      }

      leaf description {
        type string;
      }
    }

    list vdus {
      description 
          "List of Virtual Deployment Units";
      key "id";

      leaf id {
        description "Identifier of the VDU";
        type uint32;
      }

      leaf vdu-pool-name {
        description
            "Name of the VM pool to draw this VDU from. For each
             flavor of the VM a different pool is employed.";
        type leafref {
          path "/rwvdus:vdu-pool-descriptors/rwvdus:name";
        }
      }

      list internal-interfaces {
        description
            "List of external interfaces for the VNF";
        key name;

        leaf name {
          type leafref {
            path "/rwvdus:vdu-descriptors/rwvdus:ports/rwvdus:name";
          }
        }

        leaf internal-connection-point {
          type leafref {
            path "../../../internal-connection-points/id";
          }
        }
      }

      list external-interfaces {
        description
            "List of external interfaces for the VNF";
        key name;

        leaf name {
          type leafref {
            path "/rwvdus:vdu-descriptors/rwvdus:ports/rwvdus:name";
          }
        }

        leaf connection-point {
          type leafref {
            path "../../../connection-points/id";
          }
        }
      }

      uses rwmani:rwvcs-rwvm;
    }

    list vdu-dependency-list {
      description 
          "Specifies the denpencies between the VDUs.";

      key "vdu-id";
      leaf vdu-id {
        type leafref {
          path "../../vdus/id";
        }
      }

      leaf depends-on {
        type leafref {
          path "../../vdus/id";
        }
      }
    }

    list assurance-params {
      description
          "Assurance parameters specify the agreed on values for the
           specific parameter that can be monitored for the VNF.";

      key name;
      leaf name {
        type leafref {
          path "../../monitoring-params/name";
        }
      }

      leaf value {
        type uint32;
      }
    }
  }
}
