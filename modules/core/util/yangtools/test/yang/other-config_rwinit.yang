/* STANDARD_RIFT_IO_COPYRIGHT */                                                                                                                                       

/**
 * @file confif_rwinit.yang
 * @author Rajesh Ramankutty
 * @date 2014/04/23
 * @brief RiftWare CLI Commands Yang for RWinit tasklet
 */

module other-config_rwinit
{
  namespace "urn:ietf:params:xml:ns:yang:rift:rwinit";
  prefix "rwinit";

  import other-config_rwfpath_base {                                                                            
    prefix rwbase;
  }

  import rw-pb-ext {
    prefix "rwpb";
  }

  revision 2014-03-31 {
    description
      "Initial revision.";
    reference
      "RIFT Init Application";
  }

  augment /rwbase:show {
    container tasklet {
      rwpb:msg-new ShowTaskletInfo;
      rwpb:msg-flat true;
      description "Tasklet related information";
      choice  c1 {
        leaf info {
          description "Provdides tasklet related information";
	        mandatory false;
          type boolean;
			  }
      }
      choice c2 {
			  leaf resource {
          description "Provdides tasklet resource usage information";
	        mandatory false;
          type boolean;
				}
      }
    }
  }
} // module other-config_rwinit
