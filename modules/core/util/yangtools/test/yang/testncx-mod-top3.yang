/* STANDARD_RIFT_IO_COPYRIGHT */

/**
 * @file testncx-mod-top3.yang
 * @author Tom Seidenberg
 * @date 2014/03/25
 * @brief yangncx test file for modules
 */

module testncx-mod-top3
{
  namespace "http://riftio.com/ns/core/util/yangtools/tests/testncx-mod-top3";
  prefix "tnmt3";

  import testncx-mod-base5 { prefix "tnmb5-t3"; }
  import testncx-mod-a6 { prefix "tnma6-t3"; }

  description "Module testing for yangncx.";
  revision 2014-03-25 { description "Initial version"; }

  container t3c1 {
    leaf t3c1-b5t1 {
      description "A type b5t1 from container t3c1 in top3";
      type tnmb5-t3:b5t1;
    }
    leaf t3c1-a6t1 {
      description "A type a6t1 from container t3c1 in top3";
      type tnma6-t3:a6t1;
    }
  }
}
