/* STANDARD_RIFT_IO_COPYRIGHT */
/**
 * @file test-leafref.yang
 */

module test-leafref
{
  namespace "http://riftio.com/ns/core/util/yangtools/tests/yang/test-leafref";
  prefix "tlr";

  description
    "Test leafref statement.";

  revision 2015-05-27 {
    description "Initial version"; }

  typedef tbits {
    type bits {
      bit tlr_a { position 0; }
      bit tlr_b { position 1; }
      bit tlr_c { position 2; }
      bit tlr_d { position 3; }
    }
    description "Some bits";
  }

  typedef tenum {
    type enumeration {
      enum TLR_E_A { value 1; }
      enum TLR_E_B { value 2; }
      enum TLR_E_C { value 3; }
      enum TLR_E_D { value 4; }
      enum TLR_E_E { value 12345; }
    }
  }

  container top {
    list tl {
      key "name num";
      leaf name { type string; }
      leaf num { type int32; }
      leaf bin { type binary; }
      leaf bts { type tlr:tbits; }
      leaf enu { type tlr:tenum; }
    }
  }

  container reftop {

    list llr {
      key "id";
      leaf id { type string; }

      leaf name { type string; }
      leaf num { type int32; }

      leaf rname {
        type leafref { path "/top/tl[tlr:num=current()/../num]/name"; }
      }
      leaf rnum {
        type leafref { path "../../../top/tl[name = current()/../name]/num"; }
      }
      leaf rbin {
        type leafref { path "/top/tl[name= current()/../name]/bin"; }
      }
      leaf rbts {
        type leafref { path "../../../top/tl[tlr:num =current()/../num]/bts"; }
      }
      leaf renu {
        type leafref { path "/top/tl/enu"; }
      }
    }
  }
}
