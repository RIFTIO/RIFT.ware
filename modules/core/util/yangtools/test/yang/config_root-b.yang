/*
 * STANDARD_RIFT_IO_COPYRIGHT
 *
 */

module config_root-b
{
  namespace "http://riftio.com/ns/riftware-1.0/config_root";
  prefix "root";

  revision 2013-03-21 {
    description
      "Initial revision.";
    reference
      "RIFT root configuration";
  }
} // module config_root
