module test-a-rw-ip-receiver-app
{
  namespace "http://riftio.com/ns/riftware-1.0/rw-ip-receiver-app-a";
  prefix "rw-ip-receiver-app";

  import rw-cli-ext { 
    prefix "rwcli";
  }

  import rw-pb-ext {
    prefix "rwpb";
  }
  import rw-yang-types {
    prefix "rwt";
  }
  import test-a-rw-vnf-base-types{
    prefix "rwvnfbasetypes";
  }    
  import test-a-mano-base {
    prefix "manobase";
  }
  import test-a-rw-vnf-base-config {
    prefix "rwvnfbaseconfig";
  }
  revision 2014-03-31 {
    description
      "Initial revision.";
    reference
      "RIFT Destination NAT";
  }
    
  rwpb:file-pbc-include "rwtypes.h";
    
  augment /manobase:vnf-config/manobase:vnf/rwvnfbaseconfig:network-context {
    list ip-receiver-application {
      rwpb:msg-new ConfigReceiverApp;
      rwcli:new-mode "ip-receiver-app";
            
      key "name";
      max-elements 32;
            
      leaf name {
        description "Name of IP Receiver App";
        rwpb:field-inline "true";
        rwpb:field-string-max 256;
        type string;
      }

      leaf descr-string {
        description "description comment for receiver app";
        rwpb:field-inline "true";
        rwpb:field-string-max 32;
        type string;
      }

      leaf ip-address {
        description "Address of the receiver application";
        rwpb:field-inline "true";
        type rwt:ip-address;
        rwpb:field-string-max 46;
        rwpb:field-c-type "rw_ip_addr_t";
      }
      leaf protocol {
        description "Layer 4 protocol for IP";
        type rwt:rw-ip-protocol;
      }
      leaf port {
        description "L4 port number of the receiver application";
        type uint16;
      }
      leaf data-port {
        description "Data UDP port number for the test application";
        type uint16;
      }
      leaf flow-op-batch-size {
        description "Flow add/delete operations batch size";
        type uint32;
      }
      leaf flow-op-interval-milliseconds {
        description "Flow add/delete operations batch intervals";
        type uint32;
      }
      leaf flow-op-initial-count {
        description "initial number of flows to add before starting add/del operations";
        type uint64;
      }
      leaf action {
        description "Action to be performed on received packet";
        type rwvnfbasetypes:rx-action-type;
      }
    }
  }
}
