/* STANDARD_RIFT_IO_COPYRIGHT */

/**
 * @file testy2p-top2.yang
 * @author Tom Seidenberg
 * @date 2014/10/07
 * @brief yangpbc test file for global-schema
 */

module testy2p-top2
{
  namespace "http://riftio.com/ns/core/util/yangtools/tests/testy2p-top2";
  prefix "tyt2";

  import testy2p-top1 { prefix "tyt1"; }
  import testy2p-search-node2 { prefix "tysn2"; }
  import rw-pb-ext {
    prefix "rwpb";
  }

  description "Module top2 testing for yangpbc global schema.";
  revision 2014-10-07 { description "Initial version"; }

  rpc rpc-empty {
  }

  grouping g {
    leaf lf3 { type int32; }
  }

  grouping gc {
    container c {
      leaf lfc1 { type binary; }
      uses g;
      container cc {
        uses tyt1:top1g1-leafs;
      }
    }
    uses g;
  }

  grouping gl {
    list la {
      key "k1 k2 k3";
      leaf k1 { type string; }
      leaf k2 { type int32; }
      leaf k3 { type string; /* ATTN: make me an enum */ }

      list lb {
        key "k4 k5";
        leaf k4 { type string; }
        leaf k5 { type int32; }
      }
    }
  }

  // ATTN: Should have augments of the other modules

  rpc rpc-in-only {
    input {
      leaf lf1 { type string; }
      uses gc;
    }
  }

  rpc rpc-out-only {
    output {
      leaf lf1 { type string; }
      uses gc;
    }
  }

  rpc rpc-in-out {
    input {
      leaf lfi1 { type string; }
      uses gc;
    }
    output {
      leaf lfo1 { type string; }
      container cr {
        uses tyt1:top1g1-leafs;
      }
      uses gl;
    }
  }

  notification n1 {
    leaf lf5 { type string; }
  }

  notification n2 {
    leaf lf6 { type string; }
    uses gc;
    container cn {
      uses tyt1:top1g1-leafs;
    }
  }

  notification n3 {
    leaf lf6 { type string; }
    uses gl;
    container cq {
      uses gl;
    }
  }

  container top2c {
    config false;
    description "A container that uses things with messages";
    uses gc;
    container cd {
      uses g;
    }
  }

  list topl {
    key k0;
    leaf k0 { type string; }
    uses gl;
  }

  list bkll {
    key k;

    leaf k {
      type binary;
      rwpb:field-string-max 64;
      rwpb:field-inline true;
    }

    leaf myl {
      type int32;
    }

    leaf myls {
      type string;
    }

    leaf-list ll {
      type string;
    }
  }
}
