/* STANDARD_RIFT_IO_COPYRIGHT */
/**
 * @file data_rwvcs.yang
 * @author Tim Mortsolf
 * @date 2014/5/1
 * @brief RiftWare Yang data schema for the RW.VCS
 */

module other-data_rwvcs
{
  namespace "http://riftio.com/ns/riftware-1.0/other-data_rwvcs";
  prefix "rwvcs";

  import rw-pb-ext {
    prefix "rwpb";
  }

  import rw-yang-types {
    prefix "rwt";
  }

  description "RW.VCS data definitions";

  revision 2014-05-01 {
    description "Initial revision";
    reference "None";
  }

  typedef component_type {
    type enumeration {
      enum RWCOLLECTIVE;
      enum RWSECTOR;
      enum RWCOLONY;
      enum RWCLUSTER;
      enum RWVM;
      enum RWPROC;
      enum RWTASKLET;
    }
  }

  grouping rwcolony_info {
    container rwcolony_info {
      description "";
      rwpb:msg-new RwvcsRwcolonyInfo;
      config false;
    }
  } // grouping rwcolony_info

  grouping rwcluster_info {
    container rwcluster_info {
      description "";
      rwpb:msg-new RwvcsRwclusterInfo;
      config false;
    }
  } // grouping rwcluster_info

  grouping rwvm_info {
    container rwvm_info {
      description "";
      rwpb:msg-new RwvcsRwvmInfo;
      config false;

      leaf rwvm_parent {
        type boolean;
      }

      leaf vm-ip-address {
        description "RWVM IP address";
        type rwt:ip-address;
        rwpb:field-string-max 46;
      }

      leaf pid {
        description "Process ID";
        type uint32;
      }
    }
  } // grouping rwcluster_info

  grouping rwproc_info {
    container rwproc_info {
      description "";
      rwpb:msg-new RwvcsRwprocInfo;
      config false;

      leaf rwproc_parent {
        type boolean;
      }
      
      leaf pid {
        description "Process ID";
        type uint32;
      }
    }
  }

  grouping rwtasklet_info {
    container rwtasklet_info {
      description "";
      rwpb:msg-new RwvcsRwtaskletInfo;
      config false;
    }
  }

  grouping rwcomponent_info {
    list rwcomponent_info {
      description "";
      key "instance_name";
      rwpb:msg-new RwvcsRwcomponentInfo;
      config false;

      leaf component_type {
        description "";
        type component_type;
      }

      leaf component_name {
        description "";
        type string;
      }

      leaf instance_id {
        description "";
        type uint64;
      }

      leaf instance_name {
        description "";
        type string;
      }

      leaf rwcomponent_parent {
        description "";
        type leafref {
          path "../../../rwcomponent_list/rwcomponent_info/instance_name";
        }
      }
      
      leaf-list rwcomponent_children {
        description "";
        type leafref {
          path "../../../rwcomponent_list/rwcomponent_info/instance_name";
        }
      }

      choice rwcomponent_info {
        case rwcolony_info {
          uses rwcolony_info;
        }
        case rwcluster_info {
          uses rwcluster_info;
        }
        case rwvm_info {
          uses rwvm_info;
        }
        case rwproc_info {
          uses rwproc_info;
        }
        case rwtasklet_info {
          uses rwtasklet_info;
        }
      }
    }
  }

  container data-top {
    rwpb:msg-new RwvcsData;
    config false;
  }

  
  augment "/data-top" {
    container rwvcs {
      rwpb:msg-new RwvcsDataRwvcs;
      config false;

      container rwcomponent_list {
        uses rwcomponent_info;
      }
    }
  }

  container rwcomponent_list {
    uses rwcomponent_info;
  }

  container rwcolony_list {
    uses rwcomponent_info;
  }
} // module data_rwvcs
