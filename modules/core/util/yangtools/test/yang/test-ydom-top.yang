/* STANDARD_RIFT_IO_COPYRIGHT */

/**
 * @file test-ydom-top.yang
 * @author Tom Seidenberg
 * @date 2014/05/13
 * @brief Top-level yang for XMLManagerYang testing
 */

module test-ydom-top
{
  namespace "http://riftio.com/ns/yangtools/test-ydom-top";
  prefix "t";

  import rw-pb-ext { prefix "rwpb"; }
  import test-rwapis { prefix "test-rwapis"; }

  description "Top-level yang for testing XMLManagerYang";
  revision 2014-05-13 { description "Split from testncx"; }

  typedef global-enum {
    description "A typedefined global enumeration. This should work differently
                 than a typedef inside a container or non-typedefed enum. Should
                 be available in other modules";
    type enumeration {
      enum first { value 1; }
      enum second{ value 3; }
      enum seventh { value 7;}
    }
    default seventh;
  }

  typedef my-enum {
    type enumeration {
      enum ab { value 100; }
      enum cd { value 999; }
      enum gh { value 555; }
    }
  }

  container enum-test {
    rwpb:msg-new TydtEnum;
    description " A container geared towards testing enumerations ";
    
    typedef container-enum {
      description " A typedefined enumeration within a conainer";
      type enumeration {
        enum first { value 10;}
        enum second { value 20;}
        enum seventh {value 70; }
      }
      default second;
    }

    leaf global {
      description "An element from the global typdef ";
      type global-enum;
    }

    leaf local {
      description "An element from a local typedef";
      type container-enum;
      default first;
    }

    leaf local1 {
      description "An element1 from a local typedef";
      type container-enum;
      default second;
    }

    leaf mytype {
      type my-enum;
      default gh;
    }

    leaf not-typed {
      description "From an non-typed enumeration ";
      type enumeration {
        enum first { value 100;}
        enum second { value 234;}
        enum seventh { value 999;}
      }
      default seventh;
    }
  }
  
  identity company { description "A company"; }
  identity riftio { base company; description "rift.IO"; }
  identity google { base company; description "Google"; }

  typedef flags {
    type bits {
      bit a { position 0; }
      bit b { position 1; }
      bit c { position 2; }
      bit d { position 3; }
    }
  }

  typedef union1 {
    type union {
      type string;
      type flags;
      type identityref { base company; }
      type int8;
      type decimal64 { fraction-digits 14; }
    }
  }

  typedef enum1 {
    type enumeration {
      enum RWCAT_E_A { value 1; }
      enum RWCAT_E_B { value 2; }
      enum RWCAT_E_C { value 3; }
      enum RWCAT_E_D { value 4; }
      enum RWCAT_E_E { value 12345; }

    }
  }

  grouping group-a {
    container cont-in-a {
      description "Test container in group-a.";

      leaf str1 {
        description "A string from a";
        type string {
          length "1|2|10..20";
        }
      }

      leaf num1 {
        description "A number from a";
        type int64;
      }

      leaf emun_type {
        type enum1;
        default RWCAT_E_E;
      }
      
      leaf-list ll {
        description "A leaf-list of enums";
        rwpb:field-inline-max "1024";
        rwpb:field-inline true;
        type enum1;
      }

      leaf-list ls {
        rwpb:field-inline-max "10";
        rwpb:field-string-max "64";
        rwpb:field-inline true;
        type string;
      }

      list lst {
        description "A plain list";
        key "str2";
        max-elements 1024;

        leaf num2 {
          description "A number";
          type int32 { range "1..10"; }
        }

        leaf str2 {
          description "A string";
          type string;
        }
      }
    }
  }

  container top {
    rwpb:msg-new TydtTop;

    container a {
      description "for test RwYangDom.Merge";
      uses group-a;
    }

    container empty_leaf {
      description "for test RwYangDom.EmptyLeaf";
      leaf empty1 { type empty; }
      leaf empty2 { type empty; }
      leaf bool1 { type boolean; }
      leaf bool2 { type boolean; }
      leaf bool3 { type boolean; }
    }

    container empty_cont {
      description "for test RwYangDom.PresenceCont";
      presence true;

      // empty presence containers
      container ep01 {
        presence true;
      }
      container ep02 {
        presence true;
      }

      // non-presence containers
      container ep10 {
        leaf lf10 { type string; default "def10"; }
      }
      container ep11 {
        leaf lf11 { type string; default "def11"; }
      }
      container ep12 {
        leaf lf12 { type string; default "def12"; }
      }
      container ep14 {
        leaf lf14 { type string; }
      }
      container ep15 {
        leaf lf15 { type string; }
      }
      container ep16 {
        leaf lf16 { type string; }
      }

      // presence containers with optional nodes
      container ep20 {
        presence true;
        leaf lf20 { type string; default "def20"; }
      }
      container ep21 {
        presence true;
        leaf lf21 { type string; default "def21"; }
      }
      container ep22 {
        presence true;
        leaf lf22 { type string; default "def22"; }
      }
      container ep24 {
        presence true;
        leaf lf24 { type string; }
      }
      container ep25 {
        presence true;
        leaf lf25 { type string; }
      }
      container ep26 {
        presence true;
        leaf lf26 { type string; }
      }

      // presence containers with mandatory nodes
      container ep36 {
        presence true;
        leaf lf36 { mandatory true; type string; }
      }
      container ep37 {
        presence true;
        leaf lf37 { mandatory true; type string; }
      }

      // empty non-presence containers
      container ep43 {
      }
      container ep44 {
      }

      // non-presence containers with mandatory nodes
      container ep55 {
        leaf lf55 { mandatory true; type string; }
      }
    }

    container empty_cont_flat {
      description "for test RwYangDom.PresenceCont";
      presence true;
      rwpb:msg-flat true;

      // empty presence containers
      container ep01 {
        presence true;
      }
      container ep02 {
        presence true;
      }

      // non-presence containers
      container ep10 {
        leaf lf10 { type string { length "0..20"; } default "def10"; }
      }
      container ep11 {
        leaf lf11 { type string { length "0..20"; } default "def11"; }
      }
      container ep12 {
        leaf lf12 { type string { length "0..20"; } default "def12"; }
      }
      container ep14 {
        leaf lf14 { type string { length "0..20"; } }
      }
      container ep15 {
        leaf lf15 { type string { length "0..20"; } }
      }
      container ep16 {
        leaf lf16 { type string { length "0..20"; } }
      }

      // presence containers with optional nodes
      container ep20 {
        presence true;
        leaf lf20 { type string { length "0..20"; } default "def20"; }
      }
      container ep21 {
        presence true;
        leaf lf21 { type string { length "0..20"; } default "def21"; }
      }
      container ep22 {
        presence true;
        leaf lf22 { type string { length "0..20"; } default "def22"; }
      }
      container ep24 {
        presence true;
        leaf lf24 { type string { length "0..20"; } }
      }
      container ep25 {
        presence true;
        leaf lf25 { type string { length "0..20"; } }
      }
      container ep26 {
        presence true;
        leaf lf26 { type string { length "0..20"; } }
      }

      // presence containers with mandatory nodes
      container ep36 {
        presence true;
        leaf lf36 { mandatory true; type string { length "0..20"; } }
      }
      container ep37 {
        presence true;
        leaf lf37 { mandatory true; type string { length "0..20"; } }
      }

      // empty non-presence containers
      container ep43 {
      }
      container ep44 {
      }

      // non-presence containers with mandatory nodes
      container ep55 {
        leaf lf55 { mandatory true; type string { length "0..20"; } }
      }
    }

    container apis_test {
      description "for test RwYangDom.ApiTest";
      leaf lint8 { type int8; }
      leaf lint16 { type int16; }
      leaf lint32 { type int32; }
      leaf lint64 { type int64; }
      leaf luint8 { type uint8; }
      leaf luint16 { type uint16; }
      leaf luint32 { type uint32; }
      leaf luint64 { type uint64; }
      leaf lboolean { type boolean; }
      leaf lempty { type empty; }
      leaf ldecimal64 { type decimal64 { fraction-digits 10; } }
      leaf lenum { type enum1; }
      leaf lstring { type string; }
      leaf lbinary { type binary; }
      leaf newuint32 { type uint32; }
      leaf newuint64 { type uint64; }
      leaf newstring { type string; }
      leaf lbits { type flags; }
      leaf lidref { type identityref { base "company"; } }
      leaf llref { type leafref { path "../reallist/k"; } }
      leaf linstid { type instance-identifier; }
      leaf lunion { type union1; }
      // ATTN: Not supported by confd: anyxml axml;
      leaf-list leaflist { type string; }
      leaf-list primlist { type int32; }
      list reallist {
        key "k";
        leaf k { type string; }
        leaf d1 { type string; }
        leaf d2 { type uint32; }
      }
      container ntest {
        leaf str1 { type string; }
        leaf str2 { type string; }
        leaf str3 { type string; }
      }
      container binary_test {
        description "Test binary types";
        leaf binary1 { type binary; default "ChQeKNEA/4A=";}
        leaf binary2 { type binary { length "2..1024"; } default "DxAREhMUFRYXGBkaGxwdHh8gISIjJCUmJwD//v3IgARE";}
        leaf binary3 { type binary; }
        leaf binary4 { type binary; }
        leaf-list binary_list {
          description "Test Binary leaf-list";
          type binary;
        }
      }
    }
  }

  // OMG- This is really a long augment..
  augment
      /test-rwapis:config/test-rwapis:manifest/test-rwapis:profile/test-rwapis:init-phase/test-rwapis:rwvcs/test-rwapis:component/test-rwapis:component/test-rwapis:rwvcs-rwvm/test-rwapis:rwvm/test-rwapis:event-list/test-rwapis:event/test-rwapis:action/test-rwapis:action/test-rwapis:start/test-rwapis:start {

    list dl1 {
      description "Deep List with multiple keys for test";

      key "mykey1 mykey2 mykey3 mykey4 mykey5 mykey6 mykey7";
      leaf mykey1 { type string; rwpb:field-inline "true"; rwpb:field-string-max 64; }
      leaf mykey2 { type int32; }
      leaf mykey3 { type uint32; }
      leaf mykey4 { type string; rwpb:field-inline "true"; rwpb:field-string-max 64; }
      leaf mykey5 { type string; rwpb:field-inline "true"; rwpb:field-string-max 64; }
      leaf mykey6 { type string; rwpb:field-inline "true"; rwpb:field-string-max 64; }
      leaf mykey7 { type uint32; }

      container dc1 {

        leaf temp { type binary; }
        container dc2 {

          leaf test { type string; }
          list dl2 {

            key "keyl2";
            leaf keyl2 { type string; }
            leaf mtu { type uint32; }

            container dc3 {

              leaf test1 { type string; }
              list dl3 {
                config false;

                leaf terml1 { type string; }
                leaf terml2 { type binary; }
                leaf terml3 { type uint32; }
              }
            }
          }
        }
      }
    }
  }

  rpc start-test {
    input {
      leaf test-type {
        type string;
      }
      leaf publishers {
        type uint32;
      }
      leaf subscribers {
        type uint32;
      }
      leaf parallel-xact-limit {
        type uint32;
      }
      leaf xact-operation {
        type string;
      }
      leaf tasklet-type {
        type string;
      }
      container payload {
        leaf length {
          type uint32;
        }
        leaf pattern {
          type string;
        }
      }
      list lnode {
        key "key1 key3 key2";
        leaf value1 {
          type string;
        }
        leaf value2 {
          type string;
        }

        leaf key1 {
          type string;
        }

        leaf value3 {
          type string;
        }

        leaf key2 {
          type string;
        }

        leaf key3 {
          type string;
        }

        leaf value4 {
          type string;
        }
      }
    }
    output {
      leaf test-id {
        type uint32;
      }
    }
  }

  list order_test {
    key "key1 key2 key3";
    leaf value1 {
      type string;
    }
    leaf key1 {
      type string;
    }
    leaf key2 {
      type string;
    }
    leaf key3 {
      type string;
    }
    leaf value2 {
      type string;
    }
    leaf value3 {
      type string;
    }
  }

  list defaults_test {
    key "name";
    leaf name {
      type string;
    }

    leaf nd_leaf {
      type string;
    }

    leaf d_leaf {
      type string;
      default "default_val";
    }

    container d_cont1 {
      leaf nd_c1 {
        type string;
      }

      container d_cont2 {
        leaf d_c2 {
          type int32;
          default 271;
        }
        leaf nd_c2 {
          type int32;
        }
      }

      leaf d_c1 {
        type string;
        default "d_c1_val";
      }

      choice ch {
        default d_case;
        case nd_case {
          leaf nd_case_d_leaf {
            type string;
            default "nd_case_leaf_val";
          }
          leaf nd_case_nd_leaf {
            type uint32;
          }
        }
        case d_case {
          leaf d_case_nd_leaf {
            type uint32;
          }
          leaf d_case_d_leaf {
            type uint32;
            default 314;
          }
        }
      }
    }
  }

  rpc defaults_rpc {
    input {
      leaf nd_leaf {
        type string;
      }
      leaf d_leaf {
        type string;
        default "d_leaf_val";
      }
      container d_cont {
        leaf d_cont_d_leaf {
          type uint32;
          default 314;
        }
        leaf d_cont_nd_leaf {
          type uint32;
        }
      }
    }
    output {
      list d_list {
        key "name";
        leaf name {
          type string;
        }
        leaf nd_leaf {
          type uint32;
        }
        leaf d_leaf {
          type uint32;
          default 108;
        }
      }
    }
  }
}
