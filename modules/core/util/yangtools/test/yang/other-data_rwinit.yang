/* STANDARD_RIFT_IO_COPYRIGHT */                                                                                                                                       

/**
 * @file data-rwinit.yang
 * @author Rajesh Ramankutty
 * @date 2014/04/24
 * @brief RiftWare CLI Results Yang for RWinit tasklet
 */

module other-data_rwinit
{
  namespace "urn:ietf:params:xml:ns:yang:rift:rwinit";
  prefix "rwinit";

  /*
  import other-config_rwfpath_base {                                                                            
    prefix rwbase;
  }
  */

  import rw-pb-ext {
    prefix "rwpb";
  }

  revision 2014-03-31 {
    description
      "Initial revision.";
    reference
      "RIFT Init Application";
  }

 container return_status {
    rwpb:msg-new ReturnStatus;
    rwpb:msg-flat true;
    rwpb:field-inline "true";                                                                                                                                          

    leaf error_number {
      type int32;
      description "Error number";
    }
    leaf error_string {
      type string;
      rwpb:field-string-max 128;
      description "Error string value";
    }
  }

 container show_tasklet_info_rsp {
    rwpb:msg-new ShowTaskletInfoRsp;
    rwpb:msg-flat true;
    rwpb:field-inline "true";                                                                                                                                          

    list tasklet {
      rwpb:field-inline-max yang;
      max-elements 8;

      key "id";

      leaf id {
        type string;
        rwpb:field-string-max 64;
        description "Task Identifier";
      }

      leaf state {
        type string;
        rwpb:field-string-max 32;
        description "Tasklet State - INIT/RUNNING/DEAD";
      }
    }
  }

 container show_tasklet_resource_rsp {
    rwpb:msg-new ShowTaskletResourceRsp;
    rwpb:msg-flat true;
    rwpb:field-inline "true";

    list tasklet {
      rwpb:field-inline-max yang;
      max-elements 4;

      key "id";

      leaf id {
        type string;
        rwpb:field-string-max 64;
        description "Task Identifier";
      }

      list resource {
        rwpb:field-inline-max yang;
        max-elements 30;

	key "address";

        leaf name {
          type string;
          rwpb:field-string-max 64;
          description "Name of the data-type";
	}
	leaf size {
          type uint32;
          description "Size of the data allocated";
	}
	leaf count {
          type uint32;
          description "Count of number of allocations";
	}
	leaf address {
          type uint64;
          description "Size of the data allocated";
	}
	leaf location {
          type string;
          rwpb:field-string-max 256;
          description "Location from which the data is allocated";
	}
      }
    }
  }
} // module other-data_rwinit
