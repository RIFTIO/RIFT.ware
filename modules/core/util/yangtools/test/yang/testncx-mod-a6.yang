/* STANDARD_RIFT_IO_COPYRIGHT */

/**
 * @file testncx-mod-a6.yang
 * @author Tom Seidenberg
 * @date 2014/03/25
 * @brief yangncx test file for modules
 */

module testncx-mod-a6
{
  namespace "http://riftio.com/ns/core/util/yangtools/tests/testncx-mod-a6";
  prefix "tnma6";

  import testncx-mod-base4 { prefix "tnmb4-a6"; }

  description "Module testing for yangncx.";
  revision 2014-03-25 { description "Initial version"; }

  typedef a6t1 {
    type tnmb4-a6:b4t1;
    description "A typedef of b4t1 from base4, in a6";
  }
}
