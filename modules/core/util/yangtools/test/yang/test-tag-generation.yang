/* STANDARD_RIFT_IO_COPYRIGHT */

/**
 * @file test-tag-generation.yang
 * @author Rajesh Velandy
 * @date 2014/09/03
 * @brief yang for testing tag generation in NCX/yangpbc
 */

module test-tag-generation
{
  namespace "http://riftio.com/ns/core/util/yangtools/tests/test-tag-generation";
  prefix "ttg";

  import test-tag-generation-base { prefix "ttgb"; }
  import rw-pb-ext { prefix "rwpb"; }

  description
    "yang for testing Tag generation.";

  revision 2014-09-03 {
    description "Initial version"; }

  grouping abc-grp-1 {
    container abc-cont1 {
      config true;
      description "Test container 1 in abc-grp-1.";
      rwpb:msg-new TtgAbcGrpCont1;
      rwpb:msg-flat "true";

      leaf abc-str1 {
        description "A string from abc-cont 1";
        rwpb:field-string-max 64;
        type string {
          length "1..64";
        }
      }
      leaf abc-num1 {
        description "A number from abc-cont 1";
        type int64;
      }
    }
  }

  container abc-top-cont1 {
    description "A top container 1";
    rwpb:msg-new TtgAbcTopCont1;

    leaf abc-top-str1 {
      description "A string from cont 1";
      type string {
        length "1..20";
      }
    }

    uses abc-grp-1;

    uses ttgb:base-grp-1;

    uses ttgb:base-grp-2;

  }
  augment "/ttgb:top-cont1" {
    leaf new-top-str {
      description "A new string leaf";
      type string {
        length "30";
      }
    }
  }
}
