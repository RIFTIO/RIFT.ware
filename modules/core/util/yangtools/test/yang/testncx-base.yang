/* STANDARD_RIFT_IO_COPYRIGHT */

/**
 * @file testncx-base.yang
 * @author Tom Seidenberg
 * @date 2014/03/05
 * @brief Base yang for testing libncx.
 */

module testncx-base
{
  namespace "http://riftio.com/ns/core/util/yangtools/tests/testncx-base";
  prefix "tnb";

  import rw-pb-ext { prefix "rwpb"; }

  description
    "Base yang for testing libncx.";

  revision 2014-03-05 {
    description "Initial version"; }

  typedef ufnt {
    type int64;
    units "microfortnight";
    description "Approximately a second";
  }

  typedef enum_e {
    type enumeration {
      enum TNB_E_A { value 1; }
      enum TNB_E_B { value 2; }
      enum TNB_E_C { value 3; }
      enum TNB_E_D { value 4; }
      enum TNB_E_E { value 12345; }
    }
  }

  leaf x {
    type enum_e;
  }
  identity company {
    description "A company";
  }

  identity riftio {
    base company;
    description "RIFT.io";
  }

  grouping group-a {
    container cont-in-a {
      config true;
      description "Test container in group-a.";
      rwpb:msg-new TncxbGrpA;

      leaf str1 {
        description "A string from a";
        type string {
          length "1|2|10..20";
        }
      }

      leaf num1 {
        description "A number from a";
        type int64;
      }

      leaf-list ll {
        description "A leaf-list of enums";
        rwpb:field-inline-max "1024";
        type enumeration {
          enum RWCAT_E_A { value 1; }
          enum RWCAT_E_B { value 2; }
          enum RWCAT_E_C { value 3; }
          enum RWCAT_E_D { value 4; }
          enum RWCAT_E_E { value 12345; }
        }
      }

      list lst {
        description "A plain list";
        key "str2";
        max-elements 1024;

        leaf num2 {
          description "A number";
          type int32 { range "1..10"; }
        }

        leaf str2 {
          description "A string";
          type string;
        }

      }
    }

    leaf-list ll {
      description "A leaf-list of times";
      type ufnt;
    }
  }

  grouping group-b {
    leaf str3 {
      description "A string from b";
      type string;
    }

    leaf num3 {
      description "A number from b";
      type int8;
    }

    choice ch {
      description " The problem of choice";
      case c1 {
        leaf ch1-1 {
          description "Comes with many cases";
          type string;
        }
        leaf ch1-2 { type string; }
      }

      case c2 {
        leaf ch2-1 { type string; }
        leaf ch2-3 { type string; }
        choice ch-a {
          case c2-a {
            leaf ch2-2-1 {type string; }
          }
          case c3-a {
            leaf ch2-2-2 {type string;}
          }
        }
      }

      case c3 {
        container ch3-1 {
          choice ch {
            case c2 {
              leaf ch2-2-1 {type string; }
            }
            case c3 {
              leaf ch2-2-2 {type string;}
            }
          }
          leaf ch3-l1 { type string; }
          leaf ch3-l2 { type string; }
          leaf ch3-l3 { type string; }
        }
      }
    }
  }

  container top {
    leaf a-little-bit { type string; }
  }
}
