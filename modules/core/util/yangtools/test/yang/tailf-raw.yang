/* STANDARD_RIFT_IO_COPYRIGHT */
/**
 * @file tailf-raw.yang
 * @author Tom Seidenberg
 * @date 2014/08/12
 * @brief Test tail-f yang annotations. This is the raw, unannotated file.
 */

module tailf-raw
{
  namespace "http://riftio.com/ns/core/util/yangtools/tests/tailf-raw";
  prefix "tfr";

  typedef e1 {
    type enumeration {
      enum lf1;
      enum lf2;
      enum n1;
    }
  }

  notification n1 {
    leaf lf4 { type string; }
  }

  rpc r1 {
    input {
      leaf lf1 { type string; }
    }
    output {
      leaf lf5 { type string; }
    }
  }

  grouping g1 {
    leaf lf1 { type string; }
    leaf lf2 { type string; }
  }

  container top1 {
    uses g1;

    // These 2 have a hash collision (thank you, birthday paradox!)
    leaf lf588506805 { type string; }
    leaf lf116142732 { type string; }

    leaf lf3 { type string; }
    leaf n1 { type string; }
  }

  container top2 {
    config false;
    list ls1 {
      leaf-list ll1 { type string; }
    }
  }
}
