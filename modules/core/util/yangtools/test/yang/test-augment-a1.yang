/* STANDARD_RIFT_IO_COPYRIGHT */

/**
 * @file test-augment-a1.yang
 * @author Tom Seidenberg
 * @date 2014/04/04
 * @brief yangncx test file for augments
 */

module test-augment-a1
{
  namespace "http://riftio.com/ns/core/util/yangtools/test/yang/test-augment-a1";
  prefix "tauga1";

  import test-augment-b1 { prefix "taugb1"; }
  import rw-pb-ext { prefix "rwpb"; }

  description "Augment testing for yangncx.";
  revision 2014-04-04 { description "Initial version"; }

  augment /taugb1:b1_c/taugb1:b1_c1 {
    rwpb:msg-new A1C1;

    container a1_c1 {
      leaf a1_f1 { type uint32; }
    }

    container a1_c2 {
      leaf a1_f1 { type uint32; }
    }

    container a1_c3 {
      leaf a1_f1 { type uint32; }

      container a1_c1 {
        leaf a1_f1 { type uint32; }
      }

      list a1_l1 {
        key a1_f1;
        leaf a1_f1 { type uint32; }

        container a1_c1 {
          leaf a1_f1 { type uint32; }
        }
      }
    }
  }

  augment /taugb1:b1_c {
    rwpb:msg-new A1C;

    container a1_c1 {
      leaf a1_f1 { type uint32; }
    }

    container a1_c2 {
      leaf a1_f1 { type uint32; }
    }

    leaf a1_f1 { type uint32; }

    leaf a1_f2 { type uint32; }

    list a1_l1 {
      key a1_f1;
      leaf a1_f1 { type uint32; }

      container a1_c1 {
        leaf a1_f1 { type uint32; }
      }
    }
  }

  augment /taugb1:b1_c2 {
    description
      "This is a test of augmenting a module with another module's
      grouping - and nothing else.  The idea is to verify that yangpbc
      can detect this kind of augment and generate a new message
      definition.";
    uses taugb1:b1g2;
  }


  // Augment a choice
  augment /taugb1:b1_c/taugb1:b1ch1 {
    case aug1-l1 {
      leaf aug1-l1 { type string; }
    }
    // libncx bug: leaf aug1-l2 { type string; }
    case aug1-c1 {
      container aug1-c1 {
        leaf cl1 { type string; }
      }
    }
    // ATTN: libncx bug: test-augment-a1.yang:96: error:
    //   there is already a child node to "aug1-c2" at test-augment-a1.yang:95
    //   with the name "cl2" defined at test-augment-a1.yang:96
    // container aug1-c2 {
    //   leaf cl2 { type string; }
    // }
  }

  // Augment a case
  augment /taugb1:b1_c/taugb1:b1ch1/taugb1:b1ch1-c1 {
    leaf aug1_leaf { type string; }
    container aug1_cont {
      leaf lfstr { type string; }
    }
  }

  // Augment a case
  augment /taugb1:b1_c/taugb1:b1ch1/taugb1:b1ch1-c2 {
    leaf aug2_leaf { type string; }
    container aug2_cont {
      leaf lfstr { type string; }
    }
  }

  // Augment a contaner in a case
  augment /taugb1:b1_c/taugb1:b1ch1/taugb1:b1ch1-c1/taugb1:b1ch1-c1 {
    leaf lf { type string; }
    container c {
      leaf lfstr { type string; }
    }
  }

  // Augment a contaner in a case
  augment /taugb1:b1_c/taugb1:b1ch1/taugb1:b1ch1-c2/taugb1:b1ch1-c2 {
    leaf lf { type string; }
    container c {
      leaf lfstr { type string; }
    }
  }

  augment /taugb1:r1/taugb1:input/taugb1:rpcti-ch {
    case aug1-l1 {
      leaf aug1-l1 { type string; }
    }
    // libncx bug: leaf aug1-l2 { type string; }
    case aug1-c1 {
      container aug1-c1 {
        leaf cl1 { type string; }
      }
    }
    // container aug1-c2 {
    //   leaf cl2 { type string; }
    // }
  }

  augment /taugb1:r1/taugb1:input/taugb1:rpcti-ch/taugb1:c1 {
    leaf aug1_leaf { type string; }
    container aug1_cont {
      leaf lfstr { type string; }
    }
  }

  augment /taugb1:r1/taugb1:input/taugb1:rpcti-ch/taugb1:c2 {
    leaf aug2_leaf { type string; }
    container aug2_cont {
      leaf lfstr { type string; }
    }
  }

  augment /taugb1:r1/taugb1:input/taugb1:rpcti-ch/taugb1:c1/taugb1:c1 {
    leaf lf { type string; }
    container c {
      leaf lfstr { type string; }
    }
  }

  augment /taugb1:r1/taugb1:input/taugb1:rpcti-ch/taugb1:c2/taugb1:c2 {
    leaf lf { type string; }
    container c {
      leaf lfstr { type string; }
    }
  }

  augment /taugb1:r1/taugb1:output/taugb1:rpcto-ch {
    case aug1-l1 {
      leaf aug1-l1 { type string; }
    }
    // libncx bug: leaf aug1-l2 { type string; }
    case aug1-c1 {
      container aug1-c1 {
        leaf cl1 { type string; }
      }
    }
    // container aug1-c2 {
    //   leaf cl2 { type string; }
    // }
  }

  augment /taugb1:r1/taugb1:output/taugb1:rpcto-ch/taugb1:c1 {
    leaf aug1_leaf { type string; }
    container aug1_cont {
      leaf lfstr { type string; }
    }
  }

  augment /taugb1:r1/taugb1:output/taugb1:rpcto-ch/taugb1:c2 {
    leaf aug2_leaf { type string; }
    container aug2_cont {
      leaf lfstr { type string; }
    }
  }

  augment /taugb1:r1/taugb1:output/taugb1:rpcto-ch/taugb1:c1/taugb1:c1 {
    leaf lf { type string; }
    container c {
      leaf lfstr { type string; }
    }
  }

  augment /taugb1:r1/taugb1:output/taugb1:rpcto-ch/taugb1:c2/taugb1:c2 {
    leaf lf { type string; }
    container c {
      leaf lfstr { type string; }
    }
  }
}
