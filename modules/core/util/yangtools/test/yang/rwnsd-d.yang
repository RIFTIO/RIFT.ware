/*
 * STANDARD_RIFT_IO_COPYRIGHT
 *
 */

module rwnsd-d
{
  namespace "http://riftio.com/ns/riftware-1.0/rwnsd";
  prefix "rwnsd-d";

  import rw-manifest-d {
    prefix "rwmani";
  }

  import rwvnfd-d {
    prefix "rwvnfd-d";
  }

  import rwvld-d {
    prefix "rwvld-d";
  }

  import rw-pb-ext {
    prefix "rwpb";
  }

  import rw-yang-types {
    prefix rwt;
  }

  import ietf-inet-types {
    prefix "inet";
  }

  import ietf-yang-types {
    prefix "yang";
  }

  import rwmano-types-d {
    prefix "rwmanotypes";
  }

  revision 2014-10-27 {
    description
      "Initial revision. This YANG file defines 
       the Network Service Descriptor (NSD)";
    reference
      "Derived from earlier versions of base YANG files";
  }

  container nsd {
    leaf name {
      description "Network service descriptor name.";
      type string;
    }

    leaf nsd-id {
      description "UUID of the network service descriptor.";
      type yang:uuid;
    }

    leaf provider {
      description "Vendor.";
      type string;
    }

    leaf description {
      description "Description of the nsd.";
      type string;
    }

    leaf version {
      description "Version";
      type string;
    }

    list monitoring-params {
      description
          "List parameters to monitor for the network service. Examples include
           total number of sessions etc.";
      key name;
      leaf name {
        description
            "Name of the parameter to monitor.";
        type string;
      }

      leaf description {
        type string;
      }
    }

    list connection-points {
      description
          "List for external connection points. Each NS has one or more external
           connection points. As the name implies that external connection points 
           are used for connecting the NS to other NS or to external networks.
           Each NS exposes these connection points to the orchestrator. The 
           orchestrator can construct network services by connecting the
           connection points between different NS.";

      key "id";
      leaf id {
        description
            "Identifier for the external connection points";
        type uint32;
      }

      leaf cp-type {
        description
            "Type of the connection point.";
        type rwmanotypes:connection-point-type;
      }
    }

    list constituent-vnfs {
      description
          "List of VNFs that are part of this network service.";
      key vnf-id;
      leaf vnf-id {
        type leafref {
          path "/rwvnfd-d:vnfd/rwvnfd-d:vnfd-id";
        }
      }
    }  

    list vnf-dependencies {
      description 
          "List the VNF dependencies. This controls the order in which
           the VNFs are started by the NFVO.";
      key vnf-id;
      leaf vnf-id {
        type leafref {
          path "/rwvnfd-d:vnfd/rwvnfd-d:vnfd-id";
        }
      }

      leaf depends-on {
        type leafref {
          path "/rwvnfd-d:vnfd/rwvnfd-d:vnfd-id";
        }
      }
    }

    list constituent-vlds {
      description
          "List of virtual links that are part of this VNF.";
      key vld-id;
      leaf vld-id {
        type leafref {
          path "/rwvld-d:vld/rwvld-d:vld-id";
        }
      }
    }

    list assurance-params {
      description
          "Assurance parameters specify the agreed on values for the
           specific parameter that can be monitored for the NS.";

      key name;
      leaf name {
        type leafref {
          path "../../monitoring-params/name";
        }
      }

      leaf value {
        type uint32;
      }
    }
  }
}
