/*
 * STANDARD_RIFT_IO_COPYRIGHT
 *
 */

module rw-log-d
{
  namespace "http://riftio.com/ns/riftware-1.0/rw-log";
  prefix "rwlog";

  import rw-pb-ext {
    prefix "rwpb";
  }

  import rw-notify-ext-d {
    prefix "rwnotify";
  }

  revision 2014-05-29 {
    description
      "Initial revision. This YANG file defines common groupings, typedefs, and
       containers available on Riftware for logging";
    reference
      "Derived from earlier versions of base YANG files";
  }
  typedef log-severity {
    type enumeration {
      enum emergency;
      enum alert;
      enum critical;
      enum error;
      enum warning;
      enum notice;
      enum info;
      enum debug;
    }
  }

// ATTN: update rwlog_category_list.h as well while adding new category here 
// Event Log ID namespace Conventions:
// Leaving adequate gaps for expansion or allocation to newer apps
// rw-fpath  : 00001000 - 00001999 
// rw-vcs    : 00010000 - 00010999 
// rw-appmgr : 00020000 - 00020999
// rw-dts-api: 00030000 - 00030999
// rw-dts-rtr: 00040000 - 00040999
//
//

  typedef log-category {
    type enumeration {
      enum all;
      enum rw-fpath;
      enum rw-vcs;
      enum rw-appmgr;
      enum rw-dts-api;
      enum rw-dts-router;
      enum rw-log;
      enum rw-logtest;
    }
  }

  typedef direction_type {
    type enumeration {
      enum INBOUND;
      enum OUTBOUND;
    }
  }

  typedef protocol_type {
    type enumeration {
      enum IP;
      enum TCP;
      enum UDP;
      enum ETHERNET;
      enum GTP;
    }
  }

  grouping packet-info {
    container pkt-info {
    rwpb:field-inline "true";
    description "Different protocol prints need different arguments. This
        container holds all the fields needed by various protocol print
        functions";
      leaf packet-direction {
        description "Either inbound or outbound direction";
        type direction_type;
      }
      leaf packet-type {
        description "Packet protocol type";
        type protocol_type;
      }
      leaf sport {
        description "Source port needed for GTP print";
        type uint16;
      }
      leaf dport {
        description "Destination port for GTP print";
        type uint16;
      }
      leaf ip-header {
        description "IP header pointer needed for TCP/UDP prints";
        type uint64;
      }
      leaf fragment {
        description "Whether packet is fragmented or not. Needed for tcp and udp
            prints";
        type uint32;
      }
    }
  }

  grouping common-attrs  {
    leaf version98765  {
      rwpb:field-inline "true";
      type uint32;
      rwnotify:log-common;
    }
    leaf sequence {
      rwpb:field-inline "true";
      type uint64;
      rwnotify:log-common;
    }
    leaf sec {
      rwpb:field-inline "true";
      type uint32;
      rwnotify:log-common;
    }
    leaf usec {
      rwpb:field-inline "true";
      type uint32;
      rwnotify:log-common;
    }
    leaf system-id{
      rwpb:field-inline "true";
      type uint32;
      rwnotify:log-common;
    }
    leaf hostname {
      type string;
      rwnotify:log-common;
      rwpb:field-inline "true";
      rwpb:field-string-max "64";
    }
    leaf appname {
      type string; 
      rwnotify:log-common;
      rwpb:field-inline "true";
      rwpb:field-string-max "64";
    }
    leaf processid{
      rwpb:field-inline "true";
      type uint32;
      rwnotify:log-common;
    }
    leaf threadid{
      type uint32;
      rwnotify:log-common;
    }
    leaf filename {
      type string;
      rwnotify:log-common;
      rwpb:field-inline "true";
      rwpb:field-string-max "64";
    }
    leaf linenumber{
      rwpb:field-inline "true";
      type uint32;
      rwnotify:log-common;
    }
    leaf severity{
      rwpb:field-inline "true";
      type log-severity;
    }
  }

  grouping severity-emergency {
    container template_params {
      rwpb:field-inline "true";
      uses common-attrs {
        refine severity {default emergency;}
      }
    }
  }
  grouping severity-alert {
    container template_params {
      rwpb:field-inline "true";
      uses common-attrs {
        refine severity {default alert;}
      }
    }
  }
  grouping severity-critical {
    container template_params {
      rwpb:field-inline "true";
      uses common-attrs {
        refine severity {default critical;}
      }
    }
  }
  grouping severity-error {
    container template_params {
      rwpb:field-inline "true";
      uses common-attrs {
        refine severity {default error;}
      }
    }
  }
  grouping severity-warning {
    container template_params {
      rwpb:field-inline "true";
      uses common-attrs {
        refine severity {default warning;}
      }
    }
  }
  grouping severity-notice {
    container template_params {
      rwpb:field-inline "true";
      uses common-attrs {
        refine severity {default notice;}
      }
    }
  }
  grouping severity-info {
    container template_params {
      rwpb:field-inline "true";
      uses common-attrs {
        refine severity {default info;}
      }
    }
  }
  grouping severity-debug {
    container template_params {
      rwpb:field-inline "true";
      uses common-attrs {
        refine severity {default debug;}
      }
    }
  }

  grouping group-call-id {
    container call-identifier {
      rwpb:field-inline "true";
      description "Each call in Riftware is assigned a callid which is unique
                   in the context of the entity making the assignment. The
                   same call-id could be assigned by different entities - in
                   which case, the group-call-id is used in conjunction with
                   call id to provide uniqueness";
      leaf callid {
        description "The callid is defined as a grouping with a leaf that represents
                 the callid. This helps in RIFTWARE use a common tag for call-id
                 in all further uses of this grouping.";

        type uint64;
      }
      leaf groupcallid {
        description "The group call id is used to uniquely identify the assigner of
                 a call id. Each entity generating call id within RIFTWARE uses
                 group ids that are different from each other. A single entity
                 could use multiple group ids - The caveat being that none of
                 these group ids should be avaialble for other entities to use";
        type uint64;
      }
    }
  }
        
  notification ev_template {
    rwpb:msg-new EvTemplate;
    leaf eventid{type uint32; }
      description
         "EventLog for pretty Print";
      uses severity-debug;
  }
  notification fastpath-event-log-test-emergency {
    rwnotify:log-event-id 00001000;
      description
         "Testing123";
      uses severity-emergency;
      leaf data { type string; }
  }
  notification fastpath-event-log-test-alert {
    rwnotify:log-event-id 00001001;
      description
         "Testing123";
      uses severity-alert;
      leaf data { type string; }
  }
  notification fastpath-event-log-test-critical {
    rwnotify:log-event-id 00001002;
      description
         "Testing123";
      uses severity-critical;
      leaf data { type string; }
  }
  notification fastpath-event-log-test-warning {
    rwnotify:log-event-id 00001003;
      description
         "Testing123";
      uses severity-warning;
      leaf data { type string; }
  }
  notification fastpath-event-log-test-error {
    rwnotify:log-event-id 00001004;
      description
         "Testing123";
      uses severity-error;
      leaf data { type string; }
  }
  notification fastpath-event-log-test-info {
    rwnotify:log-event-id 00001005;
      description
         "Testing123";
      uses severity-info;
      leaf data { type string; }
  }
  notification fastpath-event-log-test-debug {
    rwnotify:log-event-id 00001006;
      description
         "Testing123";
      uses severity-debug;
      leaf data { type string; }
  }
  notification fastpath-event-log-test{
    rwnotify:log-event-id 00001007;
      description
         "Testing123";
      uses severity-error;
      leaf data { type string; }
  }
  notification fastpath_ev_port_state_change {
    rwnotify:log-event-id 00001002;
    description
      "CLI command audit history";
    uses severity-critical;
    leaf portnumber {
      type string;
      description "Port Name";
      rwpb:field-inline "true";
      rwpb:field-string-max "128";
    }
    leaf operstate {
      type string;
      description "Operational status";
      rwpb:field-string-max "16";
    }
    leaf serialnumber {
      type string;
      description "Serial Number";
      rwpb:field-string-max "32";
    }
  }
  notification fastpath_packet_trace {
    rwnotify:log-event-id 00001003;
    description "Packet trace";
    uses severity-error;
    leaf packet-info { type binary; }
  }

  notification callid-test {
    rwnotify:log-event-id 999;
    description "Testing123";
    uses rwlog:severity-debug;
    uses rwlog:group-call-id;
    leaf data { type string; }
  }
}
