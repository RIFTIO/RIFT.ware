module test-a-rw-dest-nat
{
  namespace "http://riftio.com/ns/riftware-1.0/rw-dest-nat-a";
  prefix "rw-dest-nat";

  import rw-cli-ext { 
    prefix "rwcli";
  }

  import rw-pb-ext {
    prefix "rwpb";
  }
  import rw-yang-types {
    prefix "rwt";
  }

  import test-a-mano-base {
    prefix "manobase";
  }
    
  import test-a-rw-vnf-base-config {
    prefix "rwvnfbaseconfig";
  }
  revision 2014-03-31 {
    description
      "Initial revision.";
    reference
      "RIFT Destination NAT Config";
  }
    
  rwpb:file-pbc-include "rwtypes.h";
    
    
  augment /manobase:vnf-config/manobase:vnf {
    container destination-nat{
      rwcli:new-mode "destination-nat";
      list fastpath{
        max-elements 16;
        key "instance";
          
        leaf instance {
          type uint32;
          description "FPATH instance number";
        }
        container resource-requirement {
          rwpb:msg-new ResourceRequirement;
          choice core-type {
            case num-cpu-core{
              leaf cpu-core-count {
                type uint32;
              }
            }
            case all {
              leaf all {
                type empty;
              }
            }
            case core-range {
              list core-range {
                rwpb:msg-flat "true";
                rwpb:field-inline "true";
                max-elements 40;
                key "start end";
                leaf start{
                  type uint32;
                }
                leaf end{
                  type uint32;
                }
              }
            }                                     
          }
        }
          
      }
    }
  }
  augment /manobase:vnf-config/manobase:vnf/rwvnfbaseconfig:network-context {
    list  lb-profile {
      rwpb:msg-new ConfigLbProfile;
      rwcli:new-mode "lb-profile";
            
      key "name";
      max-elements 32;
            
      leaf name {
        description "Name of lb-profile";
        rwpb:field-inline "true";
        rwpb:field-string-max 256;
        type string;
      }
            
      leaf descr-string {
        description "description comment for lb-profile";
        rwpb:field-inline "true";
        rwpb:field-string-max 32;
        type string;
      }
            
      list destination-nat {
        key "real-ip";
        rwpb:field-inline-max yang;
        rwpb:msg-new DestinationNatConfig;
        max-elements 32;
                
        leaf real-ip {
          type rwt:ip-address;
          rwpb:field-inline "true";
          rwpb:field-string-max 46;
          rwpb:field-c-type "rw_ip_addr_t";
        }
        leaf tcp-port {
          type uint16;
        }
        leaf udp-port {
          type uint16;
        }
        leaf source-ip {
          type rwt:ip-address;
          rwpb:field-inline "true";
          rwpb:field-string-max 46;
          rwpb:field-c-type "rw_ip_addr_t";
        }
      }
    }
    list load-balancer {
      rwpb:msg-new ConfigLoadBalancer;
      rwcli:new-mode "load-balancer";
            
      key "name";
      max-elements 32;
            
      leaf name {
        description "Name of load-balancer";
        rwpb:field-inline "true";
        rwpb:field-string-max 256;
        type string;
      }
            
      leaf descr-string {
        description "description comment for load balancer";
        rwpb:field-inline "true";
        rwpb:field-string-max 32;
        type string;
      }
            
      leaf virtual-ip {
        rwpb:field-inline "true";
        type rwt:ip-address;
        rwpb:field-string-max 46;
        rwpb:field-c-type "rw_ip_addr_t";
      }

      leaf virtual-network {
        rwpb:field-inline "true";
        type rwt:ip-prefix-non-canonical;
        rwpb:field-string-max 64;
        rwpb:field-c-type "rw_ip_prefix_t";
      }

      leaf tcp-port {
        type uint16;
      }
      leaf udp-port {
        type uint16;
      }
      leaf lb-profile {
        rwpb:field-inline "true";
        rwpb:field-string-max 256;
        type string;
      }
    }
  }
}
