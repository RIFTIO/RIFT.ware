/*
 * STANDARD_RIFT_IO_COPYRIGHT
 *
 */

module rw-vcs-c
{
  namespace "http://riftio.com/ns/riftware-1.0/rw-vcs";
  prefix "rw-vcs";

  revision 2014-10-22 {
    description "Initial revision";
    reference "RIFT Virtual Container System";
  }

  // Shitty names are because fpath defines the same RPCs and the CLI doesn't
  // understand namespaces.
  rpc vstart {
    input {
      leaf component-name {
        description "Name of the component to create a new instance of";
        type string;
        mandatory true;
      }

      leaf parent-instance {
        description "Instance-name of the parent of the new instance";
        type string;
        mandatory true;
      }
    }

    output {
      leaf rw_status {
        description "Return status of the start operation";
        type uint32;
      }

      leaf instance-name {
        description "On success, the instance-name of the started component";
        type string;
      }
    }
  }

  rpc vstop {
    input {
      leaf instance-name {
        description "Instance-name of instance to stop";
        type string;
        mandatory true;
      }
    }

    output {
      leaf rw_status {
        description "Return status of the start operation";
        type uint32;
      }
    }
  }
}
