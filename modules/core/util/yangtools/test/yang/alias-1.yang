/*
 * STANDARD_RIFT_IO_COPYRIGHT
 *
 */

module alias-1
{
  namespace "http://riftio.com/ns/core/util/yangtools/test/yang/alias-1";
  prefix "a1";

  import rw-pb-ext { prefix "rwpb"; }
  description "Test yang module";

  revision 2014-05-27 {
    description "Initial version"; 
  }

  container dup1 {
    rwpb:msg-new Dup;
    container mid {
      leaf l { type string; }
    }
  }
}
