/* STANDARD_RIFT_IO_COPYRIGHT */

/**
 * @file mangle-base.yang
 * @author Tom Seidenberg
 * @date 2014/12/11
 * @brief test name mangling
 */

module mangle-base
{
  namespace "http://riftio.com/ns/core/util/yangtools/tests/mangle-base";
  prefix "tnmb";

  import rw-pb-ext { prefix "rwpb"; }

  description
    "Base yang for testing libncx.";

  revision 2014-03-05 {
    description "Initial version"; }

  typedef ufnt {
    type int64;
    units "microfortnight";
    description "Approximately a second";
  }

  typedef enum_e {
    type enumeration {
      enum t2b_a      { value  0; }
      enum t2b_b      { value  1; }
      enum t2b_c      { value  2; }
      enum t2b_d      { value  3; }
      enum t2b_e_1d   { value  4; }
      enum t2b_f_1D   { value  5; }
      enum t2b_G1D    { value  6; }
      enum t2b_H1d    { value  7; }
      enum t2b_I_1d   { value  8; }
      enum t2b_j1dUd  { value  9; }
      enum t2b_k1_dUd { value 10; }
      enum t2b_l1DuD  { value 11; }
      enum t2b_m1D_ud { value 12; }
    }
  }

  identity company {
    description "A company";
  }

  identity riftio {
    base company;
    description "RIFT.io";
  }

  grouping group-a {
    container cont-in-a {
      config true;

      leaf-list ll {
        rwpb:field-inline-max "1024";
        type enumeration {
          enum a1aD2e3      { value  1; }
          enum b_1aD2e3     { value  2; }
          enum c1_aD2e3     { value  3; }
          enum d1a_D2e3     { value  4; }
          enum e1aD_2e3     { value  5; }
          enum f1aD2_e3     { value  6; }
          enum g1aD2e_3     { value  7; }
          enum h_1_aD2e3    { value  8; }
          enum i1_a_D2e3    { value  9; }
          enum j1a_D_2e3    { value 10; }
          enum k1aD_2_e3    { value 11; }
          enum l1aD2_e_3    { value 12; }
          enum m_1_a_D2e3   { value 13; }
          enum n1_a_D_2e3   { value 14; }
          enum o1a_D_2_e3   { value 15; }
          enum p1aD_2_e_3   { value 16; }
          enum q_1a_D2e3    { value 17; }
          enum r1_aD_2e3    { value 18; }
          enum s1a_D2_e3    { value 19; }
          enum t1aD_2e_3    { value 20; }
          enum u_1aD_2e3    { value 21; }
          enum v1_aD2_e3    { value 22; }
          enum w1a_D2e_3    { value 23; }
          enum x_1aD2_e3    { value 24; }
          enum y1_aD2e_3    { value 25; }
        }
      }

      list lst {
        key "str2";
        max-elements 1024;

        leaf num2 {
          type int32;
        }

        leaf str2 {
          type string;
        }
      }
    }

    leaf-list ll {
      description "A leaf-list of times";
      type ufnt;
    }
  }

  grouping group-b {
    leaf str3 {
      description "A string from b";
      type string;
    }

    leaf num3 {
      description "A number from b";
      type int8;
    }

    choice ch {
      description " The problem of choice";
      case c1 {
        leaf ch1-1 {
          description "Comes with many cases";
          type string;
        }
        leaf ch1-2 { type string; }
      }

      case c2 {
        leaf ch2-1 { type string; }
        leaf ch2-3 { type string; }
        choice ch-a {
          case c2-a {
            leaf ch2-2-1 {type string; }
          }
          case c3-a {
            leaf ch2-2-2 {type string;}
          }
        }
      }

      case c3 {
        container ch3-1 {
          choice ch {
            case c2 {
              leaf ch2-2-1 {type string; }
            }
            case c3 {
              leaf ch2-2-2 {type string;}
            }
          }
          leaf ch3-l1 { type string; }
          leaf ch3-l2 { type string; }
          leaf ch3-l3 { type string; }
        }
      }
    }
  }

  container top {
    leaf a-little-bit { type string; }
  }

}
