module test-a-rw-fpath-data
{
  namespace "http://riftio.com/ns/riftware-1.0/rw-fpath-data";
  prefix "rw-fpath-data";
  import rw-pb-ext {
    prefix "rwpb";
  }
  import rw-yang-types {
    prefix "rwt";
  }
    
  import test-a-rw-vnf-base-types {
    prefix "rwvnfbasetypes";
  }
  import test-a-mano-base {
    prefix "manobase";
  }
  import test-a-rw-vnf-base-opdata {
    prefix "rwvnfbaseopdata";
  }
  revision 2014-11-21 {
    description
      "Initial revision.";
    reference
      "RIFT Fpath Operational Data";
  }
  grouping cpu-usage {
    container cpu-usage {
      rwpb:msg-new CpuUsage;
      rwpb:field-inline "true";
      leaf lcore-id {
        description "lcore-id";
        type uint32;
      }
      leaf tsc-per-sec {
        description "tsc per second for fpath. For debug purpose";
        type uint64;
      }
      leaf sample-interval-in-secs {
        description "sample interval in seconds";
        type uint64;
      }
      leaf loop-count-percent {
        description "Loop count percent on max loop count that corresponds to 100 percent CPU";
        type uint64;
      }
      leaf max-loops-per-interval {
        description "max loops per interval. For debug purpose";
        type uint64;
      }
      leaf last-sample-tsc {
        description "tsc cycle when last work unit was sampled";
        type uint64;
      }
      list  work-sample-bin {
        rwpb:msg-flat "true";
        rwpb:field-inline "true";
        max-elements 60;
        leaf start-interval {
          description " Start interval in seconds since work unit was sampled";
          type uint32;
        }
        leaf end-interval {
          description "End interval interval in secs since work unit was
                sampled";
          type uint32;
        }
        leaf cpu-usage-percent {
          description "Percentage of CPU usage at specific time
                interval";
          type uint64;
        }
        leaf loops-per-interval {
          description "Loops during the specific time interval";
          type uint64;
        }
      }
    }
  }

  
  grouping flow-fields {
    list flow-field {
      rwpb:field-inline-max yang;
      max-elements 16;
      rwpb:field-inline "true";

      key "field-type";

      leaf field-type {
        type rwvnfbasetypes:flow-field-type;
      }
      leaf field-prefix-len {
        type uint8;
      }
      leaf field-value {
        description "Field value with fields in network order";
        rwpb:field-inline "true";
        rwpb:field-string-max 16;
        type binary;
      }
    }
  } //flow-fields

  typedef lb-key-extraction-method{
    type enumeration{
      enum plugin;
      enum script;
    }
  }
  
  grouping kernel-stats{
    container kernel-stats{
      rwpb:msg-new KernelKniStats;
          
      list device{
        rwpb:msg-flat "true";
        rwpb:field-inline "true";
        max-elements 128;
              
        key "name";
        leaf name{
          rwpb:field-string-max 16;
          type string;  
        }
        leaf ifindex{
          description "Kernel ifindex of the device\n";
          type uint32;
        }
              
        leaf rx-packets{
          description "Number of packets recevied by the kernel from fastpath\n";
          type uint64;
        }
              
        leaf rx-as-tx-packets{
          description "Number of packets recevied by the kernel from fastpath in egress direction with respect to fastpath (application->fastpath)\n";
          type uint64;
        }
        leaf rx-as-tx-filtered{
          description "Number of packets received by the kernel in egress direction which are dropped (not delivered to kernel network stack)";
          type uint64;
        }
        leaf rx-as-tx-delivered{
          description "Number of packets received by the kernel in egress direction which are delivered to kernel network stack)";
          type uint64;
        }
        leaf rx-only-packets{
          description "Number of packets received by the kernel from fastpath in ingress direction";
          type uint64;
        }
        leaf rx-only-filtered{
          description "Number of packets received by the kernel from fastpath in ingress direction but dropped before delivering to network stack";
          type uint64;
        }
        leaf rx-only-delivered{
          description "Number of packets received by the kernel from fastpath in ingress direction delivered to network stack";
          type uint64;
        }
        leaf rx-dropped{
          description "Number of packets received by the kernel from fastpath but dropped (lack of skb)";
          type uint64;
        }
        leaf rx-drop-noroute{
          description "number of packets dropped in the kernel due to failure in policy forwarding";
          type uint64;
        }
        leaf tx-packets{
          description "Number of packets sent by the kernel to fastpath";
          type uint64;
        }
              
        leaf tx-dropped{
          description "Number of packets dropped by the kernel when sending to fastpath";
          type uint64;
        }
        leaf tx-no-txq{
          description "Number of packets dropped by kernel due to lack of txq space(slow reader fastpath)";
          type uint64;
        }
        leaf tx-no-allocq{
          description "Number of packets dropped by kernel due to lack of allocq";
          type uint64;
        }
        leaf tx-enq-fail{
          description "Number of packets dropped by kernel due to enqueue fail";
          type uint64;
        }
        leaf tx-deq-fail{
          description "Number of packets dropped by kernel due to dequeue fail";
          type uint64;
        }
      }
    }
  }
  
  augment /manobase:vnf-opdata/manobase:vnf {
    container controller-info{
      config false;
      rwpb:msg-new RwFpathControllerInfo;
      leaf lead-fastpath{
        type uint32;
      }
    }
        
    list fastpath-instance{
      config false;
      rwpb:msg-new FastpathState;
      /*Need to fix it by choice on lport-type*/
      key "task-id";
            
      leaf task-id {
        type uint32;
        description "Fastpath Instance-id";
      }
      container info {
        leaf hashbin-credit{
          type uint32;
        }
      }
      container fabric-context{
        uses rwvnfbasetypes:vrf-info;
      }
      container debug {
        rwpb:msg-proto-max-size "166996";
        uses kernel-stats;
        container memory-stats {
          rwpb:msg-new MempoolStats;
          rwpb:msg-flat true;
          rwpb:field-inline "true";
          rwpb:msg-proto-max-size "166952";
          list mempool-name{
            max-elements 128;
            key "name";
            leaf name{
              description "mempool name";
              type string;
              rwpb:field-string-max 128;
            }
            leaf ring{
              description "mempool ring name";
              type string;
              rwpb:field-string-max 128;
            }
            leaf size{
              description "size";
              type uint32;
            }
            leaf header-size{
              description "header-size";
              type uint32;
            }
            leaf element-size{
              description "element size";
              type uint32;
            }
            leaf trailer-size{
              description "trailer size";
              type uint32;
            }
            leaf total-object-size{
              description "total object size";
              type uint32;
            }
            leaf private-data-size{
              description "private data size";
              type uint32;
            }
            leaf physical-address{
              type uint64;
              description "physical address";
            }
            leaf page-num{
              type uint32;
              description "page number";
            }
            leaf page-shift{
              type uint32;
              description "page shift";
            }
            leaf page-mask{
              type uint32;
              description "page mask";
            }
            leaf element-va-start{
              description "element virtual address start";
              type uint64;
            }
            leaf element-free {
              description "total elements free";
              type uint32;
            }
            leaf element-va-end{
              description "element virtual address end";
              type uint64;
            }
            list lcore-cache{
              max-elements 20;//RTE_MAX_LCORE
              key "id";
              leaf id{
                description "lcore id";
                type uint32;
              }
              leaf length{
                description "number of mbufs in cache available in the cache";
                type uint32;
              }
            }
          }
        }
      }


      list appmgr {
        config false;
        key "name id";
                
        leaf name {
          type string;
          rwpb:field-string-max 64;
          rwpb:field-inline "true";
        }
        leaf id {
          type uint32;
        }
        list local-flows {
          rwpb:msg-new FpathAppmgrLocalFlows;
          config false;
          key "context-name address protocol unique-id";

          leaf context-name{
            type string;
            rwpb:field-string-max 64;
            rwpb:field-inline "true";
          }

          leaf address {
            type rwt:ip-address;
            rwpb:field-inline "true";
            rwpb:field-string-max 64;
          }

          leaf protocol{
            type rwt:rw-ip-protocol;
          }

          leaf unique-id{
            type rwt:port-number;
          }

          leaf flow-method{
            type rwvnfbasetypes:flow-apply-method;
          }
          leaf port{
            type rwt:port-number;
          }
          leaf port-prefix-len {
            type uint32;
          }

          container nat{
            rwpb:msg-flat true;
            rwpb:field-inline "true";
            leaf address {
              type rwt:ip-address;
              rwpb:field-inline "true";
              rwpb:field-string-max 64;
            }
            leaf protocol {
              type rwt:rw-ip-protocol;
            }
            leaf port{
              type rwt:port-number;
            }
          }
          container tunnel {
            rwpb:msg-flat true;
            rwpb:field-inline "true";
            leaf tunnel_protocol {
              type rwt:rw-ip-protocol;
            }
            leaf tunnel_src_address {
              type rwt:ip-address;
              rwpb:field-inline "true";
              rwpb:field-string-max 64;
            }
            leaf tunnel_dst_address {
              type rwt:ip-address;
              rwpb:field-inline "true";
              rwpb:field-string-max 64;
            }
          }
        }
      }
    }


    list vsap{
      config false;
      key "vsap-id";
      rwpb:msg-new RwVsap;
            
      leaf vsap-id {
        type uint32;
      }
      leaf-list vfap-id-list{
        type uint32;
        max-elements 16;
      }
      leaf group-id{
        type uint32;
      }
    }
        
    list vfap {
      config false;
      key "vfap-id";
      unique "nc-id ip-address udp-port";
      rwpb:msg-new RwVfap;
            
      leaf vfap-id {
        type uint32;
      }
      leaf group-id{
        type uint32;
      }
      leaf nc-id{
        mandatory true;
        type uint32;
      }
      leaf ip-address{
        rwpb:field-inline "true";
        rwpb:field-string-max 46;
        mandatory true;
        type rwt:ip-address;
      }
      leaf udp-port{
        mandatory true;
        type uint32;
      }
    }

    list ip-flow-hashbin{
      config false;
      key "hashbin-id";
      rwpb:msg-new RwIpFlowHashBin;
            
      leaf hashbin-id {
        type uint32;
      }
      leaf fastpath_instance{
        type uint32;
      }
    
      list vsap{
        key "vsap-id";
        max-elements 16;
        rwpb:field-inline "true";
                
        leaf vsap-id {
          type uint32;
        }
      }
    }

    list ip-flow-signature{
      config false;
      key "signature-id";
      rwpb:msg-new RwIpFlowSignature;
            
      leaf signature-id{
        type uint32;
      }
      leaf signature-key{
        rwpb:field-inline "true";
        rwpb:field-string-max 256;
        type binary;
      }
      leaf signature-mask{
        rwpb:field-inline "true";
        rwpb:field-string-max 256;
        type binary;
      }
      leaf flow-type{
        type rwvnfbasetypes:flow-type;
      }
      leaf nc-id{
        type uint32;
      }
      leaf ip-prefix {
        description "prefix for the nat-pool";
        rwpb:field-inline "true";
        type rwt:ip-prefix-non-canonical;
        rwpb:field-string-max 64;
      }

      leaf addr-type {
        type rwvnfbasetypes:signature-address-type;
      }

      leaf include_l2 {
        type uint32;
      }
            
      leaf priority{
        type uint32;
      }
            
      leaf application-id{
        type uint32;
      }
            
      leaf application-data{
        type uint32;
      }
    }
        
    list classifier {
      config false;
      key "classifier-id";
      rwpb:msg-new RwIpClassifier;   
            
      leaf classifier-id{
        type uint32;
      }
            
      container user-info{
        rwpb:field-inline "true";
        leaf application-name{
          rwpb:field-inline "true";
          rwpb:field-string-max 64;
          type string;
        }
        leaf application-id{
          type uint32;
        }
        leaf application-data{
          type uint32;
        }
      }

      leaf extraction-method{
        type lb-key-extraction-method;
      }

      container cache-behavior {
        rwpb:field-inline "true";
        leaf absolute_timeout {
          type int32;
        }
      }
      
      container script-info{
        rwpb:field-inline "true";
        leaf script-info{
          rwpb:field-inline "true";
          rwpb:field-string-max 64;
          type string;
        }
      }
    } // list classifier

    container create-flow-def {
      rwpb:msg-new CreateFlowDefinition;
      rwpb:msg-flat true;
      config false;
      //leaf flow-type{
      //type flow-type;
      //}
      leaf sig-match-only {
        description "Flag to indicate if this LB signature that requires only
            signature match or also requires flow match";
        type enumeration {
          enum No;
          enum Yes;
        }
      }
      leaf tasklet-name {
        description "Tasklet name";
        rwpb:field-inline "true";
        rwpb:field-string-max 64;
        type string;
      }
      leaf tasklet-instance {
        type uint32;
        description "Tasklet instance";
      }
      leaf app-flow-index {
        type uint32;
        description "Application specific index to match request to response";
      }
      uses flow-fields;
    } // flow-def

    list create-flow-def-response {
      rwpb:msg-new CreateFlowDefinitionResponse;
      rwpb:msg-flat true;
      config false;
      rwpb:field-inline-max yang;
      max-elements 16;
      rwpb:field-inline "true";

      key "tasklet-name tasklet-instance";
      leaf tasklet-name {
        description "Tasklet name";
        rwpb:field-inline "true";
        rwpb:field-string-max 64;
        type string;
      }
      leaf tasklet-instance {
        type uint32;
        description "Tasklet instance";
      }
      leaf app-flow-index {
        type uint32;
        description "Application specific index to match request to response";
      }
      leaf return-status {
        type int32;
      }
      leaf flow-type {
        type rwvnfbasetypes:flow-type;
      }
    }

    container create-flow-def-internal {
      rwpb:msg-flat true;
      config false;
      rwpb:msg-new CreateFlowDefInternal;
      
      leaf flow-type{
        type rwvnfbasetypes:flow-type;
      }
      leaf sig-match-only {
        type enumeration {
          enum No;
          enum Yes;
        }
      }
      uses flow-fields;
    } // flow-def

    container signature-add-request {
      rwpb:msg-new SignatureAddRequest;
      rwpb:msg-flat true;

      leaf tasklet-name {
        description "Tasklet name";
        rwpb:field-inline "true";
        rwpb:field-string-max 64;
        type string;
      }
      leaf tasklet-instance {
        type uint32;
        description "Tasklet instance";
      }
      leaf ncid {
        type uint32;
      }
      leaf priority {
        type uint32;
      }
      leaf flow-type {
        type rwvnfbasetypes:flow-type;
      }
      leaf signature-addr-type {
        type rwvnfbasetypes:signature-address-type;
      }
      leaf app_id {
        type uint32;
      }
      leaf appdata {
        type uint32;
      }
      leaf include_l2 {
        type uint32;
      }
      uses flow-fields;
    }

    container signature-add-response {
      rwpb:msg-new SignatureAddResponse;
      rwpb:msg-flat true;

      leaf signature-id {
        type uint32;
        description "Signature ID";
      }
      leaf return-status {
        type int32;
      }
    }

    container signature-delete-request {
      rwpb:msg-new SignatureDeleteRequest;
      rwpb:msg-flat true;

      leaf tasklet-name {
        description "Tasklet name";
        rwpb:field-inline "true";
        rwpb:field-string-max 64;
        type string;
      }
      leaf tasklet-instance {
        type uint32;
      }
      leaf signature-id {
        type uint32;
        description "Signature ID";
      }
    }

    container signature-delete-response {
      rwpb:msg-new SignatureDeleteResponse;
      rwpb:msg-flat true;

      leaf signature-id {
        type uint32;
        description "Signature ID";
      }
      leaf return-status {
        type int32;
      }
    }
  }
  
  augment /rwvnfbaseopdata:clear-data/rwvnfbaseopdata:input/rwvnfbaseopdata:vnf{
    container kernel-counters{
      rwpb:msg-new RwFpathClearKernelCounters;
      uses rwvnfbaseopdata:vnf-key;
      leaf fastpath-instance{
        type uint32;
      }
    }
    container lacp-counters{
      rwpb:msg-new RwFpathClearLacpCounters;
      uses rwvnfbaseopdata:vnf-key;
      leaf port-name {
        rwpb:field-inline "true";
        rwpb:field-string-max 64;
        type string;
      }
    }
  }


  grouping ipproto-port-msg {
    list info {
      uses rwvnfbaseopdata:vnf-key;
      leaf ipa {
        type rwt:ip-address;
        rwpb:field-inline "true";
        rwpb:field-string-max 46;
        rwpb:field-c-type "rw_ip_addr_t";
      }
      leaf proto {
        type uint32;
      }
      leaf owner_id {
        type uint64;
      }
      leaf start_port {
        type uint32;
      }
      leaf port_range {
        type uint32;
      }
      leaf req_code {
        type enumeration {
          enum chunk_add  { value 1; }
          enum chunk_del { value 2; }
        }
      }
      leaf resp_code {
        type int32;
      }
    }
  }
  rpc ipproto-port{
    input {
      rwpb:msg-new "IpprotoPortInput";
      uses ipproto-port-msg;
    }
    output {
      uses ipproto-port-msg;
    }
  }
  
  rpc fpath-debug {
    input {
      container node {      
        rwpb:msg-new FpathDebug;
        rwpb:msg-flat "true";
        rwpb:field-inline "true";

        leaf id {
          type uint32;
        }

        choice operation {
          container show {
            description "Show operation";
            container thread {
              presence true;
              description "Information on thread";
              leaf lcore {
                type uint32;
                description "Core Id";
              }
              leaf cpu-usage {
                type empty;
                description "Information on CPU usage based on
                                  work-units completed";
              } 
            } //thread
            leaf work {
              type empty;
              description "Information on work";
            } //thread
            leaf lcore {
              type empty;
              description "Information on lcore";
            } //lcore
            container table {
              presence true;
              description "Information on FastPath related global tables";
              leaf vsapid-vfapid-bindings {
                description "VSAPID to VFAPID bindings";
                type empty;
              }
              leaf vfapid-address-bindings {
                description "VFAPID to Address bindings";
                type empty;
              }
              container fpath-hashbin-bindings {
                presence true;
                description "Fpath instance to hashbins bindings";
                leaf rwfpath-instance {
                  type int32;
                  description "Fpath instance id";
                }
              }
              leaf ip-signature-bindings {
                type empty;
                description "IP Signature Table";
              }
              leaf registered-fpath {
                type empty;
                description "Registered Fpath";
              }
              leaf classifier-service {
                type empty;
                description "Classifier services";
              }
            } // table
          } //show   
          container start {
            description "Start operation";
            container thread {
              leaf lcore {
                type uint32;
                description "Core Id";
              }
            } //thread
            leaf fast-path {
              type empty;
              description "fast path";
            } //fast-path
            leaf hashbin-distribution {
              type empty;
              description "Initiate Hashbin distribution";
            } // hashbin-distribution
            leaf fast-flow {
              type empty;
              description "Start Fast-Flow service";
            }
                        
          } //start
          container stop {
            container thread {
              description "Stop operation";
              leaf lcore {
                type uint32;
                description "Core Id";
              }
            } //thread
            leaf fast-path {
              type empty;
              description "fast path";
            } //fast-path
            leaf fast-flow {
              type empty;
              description "Stop Fast-Flow service";
            }
          } //stop
          container assign {
            description "Assign operation";             
            leaf work-id {
              type uint32;
              description "Work Id";
            }
            leaf lcore-id {
              type uint32;
              description "lcore-id";
            }          
          } //assign
          container test{
            description "Test operation";
            container rwfpath {
              description "Test operation for RW.Fpath";
              container msg-test{
                description "Messenging test";
                leaf fpctrl-instance {
                  description "RW.Fpath instance";
                  type uint32;
                }
              }
            }
            container rwfpctrl {
              description "Test operation for RW.Fpath";
              container msg-test{
                description "Messenging test";
                leaf fpath-instance {
                  description "RW.Fpath instance";
                  type uint32;
                }
              }
            }
          } // test
        } // choice
      } // node
    } // RPC fath-debug
    
    output {
      rwpb:msg-proto-max-size "1700000";
      rwpb:msg-new FpathDebugOut;
      container work-info {
        rwpb:msg-new RwWorkInfo;
        rwpb:msg-flat true;
        rwpb:msg-proto-max-size "1700000";
        
        list work {
          rwpb:field-inline-max yang;
          max-elements 256;
          
          key "id";
          
          leaf id {
            type uint32;
            description "Id";
          }
          
          leaf name {
            type string;
            rwpb:field-string-max 64;
            description "Work name";
          }
          leaf port-id {
            type rwt:port-number;
            description "Port Id";
          }
          leaf port-name {
            type rwvnfbasetypes:rwfpath-base-string;
            rwpb:field-string-max 256;
            description "Port Name";
          }
          
          leaf work-instance-id {
            type int32;
            description "Work instance Id";
          }
          leaf lcore-id {
            type int32;
            description "lcore assigned";
          }
          leaf resched-attempts {
            type int32;
            description "number of times works rescheduled to different lcores";
          }
        }
      }

      container lcore-info {
        rwpb:msg-new RwLcoreInfo;
        rwpb:msg-flat true;
        
        
        list lcore {
          rwpb:field-inline-max yang;
          max-elements 64;//RTE_MAX_LCORE
          
          key "id";
          
          leaf id {
            type uint32;
            description "Id";
          }
          
          leaf socket {
            type int32;
            description "NUMA Socket Id";
          }
          
          leaf core-id {
            type uint32;
            description "Core Id";
          }
          
          leaf thread-status {
            type string;
            rwpb:field-string-max 256;
            description "Thread Status";
          }
          
          leaf thread-type {
            type string;
            rwpb:field-string-max 256;
            description "Thread Type";
          }
          
          leaf tx-q-id {
            type uint32;
            description "Tx Q Id";
          }
          leaf num-works {
            type uint32;
            description "Num works Assigned"; 
          }
        }
      }
      
      container lcore-id-info {
        rwpb:msg-new RwLcoreIdInfo;
        rwpb:msg-flat true;
        
        
        leaf id {
          type uint32;
          description "Id";
        }
        list work {
          rwpb:field-inline-max yang;
          max-elements 32;
          
          key "work-id";
          
          leaf work-id {
            type uint32;
            description "Work Id";
          }
          
          leaf work-name {
            type string;
            rwpb:field-string-max 64;
            description "Work name";
          }
        }
      }
      container lcore_thread-info {
        rwpb:msg-new RwFpDebugLcoreThreadInfo;
        rwpb:msg-flat true;
        
        
        leaf lcore-id {
          type int32;
          description "lcore Id";
        }
        
        leaf thread-type {
          type string;
          rwpb:field-string-max 256;
          description "Thread Type";
        }
        
        leaf tx-q-id {
          type uint32;
          description "Tx Q Id";
        }
        
        list work_queue {
          rwpb:field-inline-max yang;
          max-elements 128; // TBD
          
          key "work_id";
          
          leaf work_id {
            type uint32;
            description "Work instance Id";
          }
          leaf work_name {
            type string;
            rwpb:field-string-max 64;
            description "Work name";
          }
          leaf work_flag {
            type uint16;
            description "bitmap flag for work property";
          }
          leaf work_metric {
            type uint64;
            description "work accomplished so far";
          }
          leaf work_metric_checkpoint {
            type uint64;
            description "work accomplished last snapshot";
          }
          leaf work_cont_low {
            type uint16;
            description "Number conscecute low work cycles";
          }
        } //Work Info

        list app-data {
          rwpb:field-inline-max yang;
          max-elements 4;

          key "app_id";

          leaf app_id {
            type uint32;
            description "Channel Application Id";
          }
        
          list channel-stats {
            rwpb:field-inline-max yang;
            max-elements 32;

            key "channel_id";

            leaf channel_id {
              type uint32;
              description "Channel Id";
            }
        
            leaf total-transmit {
              type uint64;
              description "Total transmitted packets";
            }

            leaf total-dropped {
              type uint64;
              description "Total dropped packets";
            }
          }
        }
      } // thread-info
      uses cpu-usage;
      container vsapid-table {
        rwpb:msg-new RwFpVsapidTable;
        rwpb:msg-flat true;
        rwpb:msg-proto-max-size "325672";
        
        list vsapid-to-vfapid {
          rwpb:field-inline-max yang;
          max-elements 512; 

          key "vsapid";
          leaf vsapid {
            type int32;
            description "Virtual Service Access Point ID";
          }
          leaf fpath {
            type int32;
            description "Fpath Instance";
          }
          leaf groupid {
            type int32;
            description "Resource Group ID";
          }
          list vfapid-list {
            description "Virtual Fabric Access Port ID list";
            max-elements 16;
            key "vfapid";

            leaf vfapid {
              description "Virtual Fabric Access Port ID";
              type int32;
            }
          } 
        } // vsapid-to-vfapid list
      }
      container vfapid-table {
        rwpb:msg-new RwFpVfapidTable;
        rwpb:msg-flat true;
        
        list vfapid-to-addr {
          rwpb:field-inline-max yang;
          max-elements 1024; 

          key "vfapid";

          leaf vfapid {
            type int32;
            description "Virtual Fabric Access Port ID";
          }
          leaf groupid {
            type uint32;
            description "Group id";
          }
          leaf fpath {
            type int32;
            description "Fpath Instance";
          }
          leaf ncid {
            type int32;
            description "Network Context ID";
          }
          leaf ip_address {
            type rwt:ip-address;
            rwpb:field-string-max 46;
            rwpb:field-c-type "rw_ip_addr_t";
            description "IP Address where VFAPID is accessible";
          }
          leaf port {
            type int32;
            description "UDP port where VFAPID is accessible";
          }
        }
      } // vfapid-table
      container hashbin-table {
        rwpb:msg-new RwFpHashbinTable;
        rwpb:msg-flat true;
        

        leaf fpath_hashbin_credits {
          type uint32;
          description "RW.Fpath hashbin credits";
        }

        leaf total_hashbin_credits {
          type uint32;
          description "Cumulative hashbin credits";
        }

        leaf total_hashbins_assigned {
          type uint32;
          description "Total hashbins assigned to this RW.Fpath Instance";
        }
        
        list hashbins {
          rwpb:field-inline-max yang;            
          max-elements 1024; 
          container hashbin-range {
            leaf hashbin-start{
              type int32;
              description "Hashbin Range Start";
            }
            leaf hashbin-end {
              type int32;
              description "Hashbin Range End";
            }            
          }
        } // hashbins
      } // hashbin-table
      container ip-signature-table {
        rwpb:msg-new RwFpIpsigTable;
        rwpb:msg-flat true;
        rwpb:msg-proto-max-size "1300000";
        
        list ip-signature {
          rwpb:field-inline-max yang;
          max-elements 1024; 

          key "sig-id";

          leaf sig-id {
            description "Signature ID";
            type uint32;
          }
          leaf flow-type {
            description "Flow Type";
            type uint32;
          }
          leaf ncid {
            description "Network Context ID";
            type uint32;
          }
          leaf ip-address {
            description "IP Address";
            type rwt:ip-address;
            rwpb:field-string-max 46;
            rwpb:field-c-type "rw_ip_addr_t";
          }
          
          leaf sig-mask {
            description "Signature Mask";
            type string;
            rwpb:field-string-max 512;
          }
          leaf sig-key {
            description "Signature Key";
            type string;
            rwpb:field-string-max 512;
          }
        }
      } // IP Signature Table
      container registered-fpath {
        rwpb:msg-new RwFpFpath;
        rwpb:msg-flat true;
        
        leaf Fpctrl-id {
          type uint32;
          description "Fpctrl instance";
        }
        
        list fpath {
          rwpb:field-inline-max yang;
          max-elements 1024; 
          key "fpath-id";
          leaf fpath-id {
            type uint32;
            description "Fpath ID";
          }
        }
      } // registered-fpath

      container classifier-service {
        rwpb:msg-new SvcTable;
        rwpb:msg-flat true;
        rwpb:msg-proto-max-size "230448";
        
        
        leaf Fpctrl-id {
          type uint32;
          description "Fpctrl instance";
        }
        
        list service_list{
          rwpb:field-inline-max yang;
          rwpb:field-inline "true";
          max-elements 256; 
          key "service-id";
          
          leaf service-id {
            type uint32;
            description "Service Id";
          }
          leaf user-application {
            type string;
            rwpb:field-string-max 256;
            description "User Application using the classifier service";
          }
          leaf ipfp-plugin-id {
            type uint32;
            description "IPFP plugin ID of user application";
          }
          list signature_list {
            rwpb:field-inline-max yang;
            rwpb:field-inline "true";
            max-elements 16; 
            key "signature-id";
            leaf signature-id {
              type uint32;
              description "Signature ID for receiver signature used by Classifier";
            }
          }
                    
          leaf key-extraction-method {
            type enumeration {
              enum plugin { value 0; }
              enum script { value 1; }
            }
            description "Key extraction mechanism";
          }
        }
      } // Classifier service
    } // output
  } // fpath_debug
}
