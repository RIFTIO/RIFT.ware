/* STANDARD_RIFT_IO_COPYRIGHT */

/**
 * @file mangle-test.yang
 * @author Tom Seidenberg
 * @date 2014/12/11
 * @brief test name mangling
 */

module mangle-test
{
  namespace "http://riftio.com/ns/core/util/yangtools/tests/mangle-test";
  prefix "tn";

  import mangle-base { prefix "tnmb"; }
  import rw-pb-ext { prefix "rwpb"; }
  import rw-cli-ext { prefix "rwcli"; }

  description
    "Top-level yang for testing libncx.";

  revision 2014-03-05 {
    description "Initial version"; }

  typedef relative-ufnt {
    type tnmb:ufnt {
      range "-10000000..10000000";
    }
    description "A few months, either way";
  }

  typedef enum_eplus {
    type tnmb:enum_e;
    description "Renamed enum_e";
  }

  typedef flags {
    type bits {
      bit a       { position   0; }
      bit b       { position   1; }
      bit c       { position   2; }
      bit d       { position   3; }
      bit e_1d    { position   4; }
      bit f_1D    { position   5; }
      bit G1D     { position   6; }
      bit H1d     { position   7; }
      bit I_1d    { position   8; }
      bit j1dUd   { position   9; }
      bit k1_dUd  { position  10; }
      bit l1DuD   { position  11; }
      bit m1D_ud  { position  12; }
    }
    description "Some bits";
  }

  identity google {
    base tnmb:company;
    description "Google";
  }

  grouping group-top {
    leaf n1 {config true; type int8 {range "-12..14";} }
    leaf n2 { type int16 {range "100..200|300|400..500";} config true; }
    leaf n3 { type int32; config false; }
    leaf n4 { type int64; config false; }
    leaf n5 { type uint8; config true; }
    leaf n6 { type uint16; config true; }
    leaf n7 { type uint32; config false; }
    leaf n8 { type uint64; config false; }

    leaf iref1 { type identityref { base "tnmb:company"; } }
    leaf bin1 { type binary {length "2..5";}}
    leaf bits1 { type flags; }
    leaf bool1 { type boolean; }
    leaf dec1 { type decimal64 { fraction-digits 10; } }
    leaf e1 { type empty; }
    leaf s1 { type string{length "2..5";} }

    // ATTN: anyxml is not supported by confd!
    //anyxml axml { config true; }

    leaf u1 {
      type union {
        type string {length "2";pattern "[p-r]*";}
        type tn:flags;
        type identityref { base "tnmb:company"; }
        type int8 {range "100..110";}
        type tn:relative-ufnt;
        type decimal64 {fraction-digits "14";}
      }
    }
  }

  container top {

    rwpb:msg-new TncxTop;

    container a {
      rwcli:new-mode "test-new-mode";
      uses tnmb:group-a;
    }

    container a1 {
      uses tnmb:group-a {
        augment "cont-in-a" {
          leaf aug1 { type string; description "An augment"; }
        }
      }
    }

    container b {
      uses tnmb:group-b;
    }

    container c {
      leaf c {
        type identityref { base "tnmb:company"; }
      }
    }

    container e {
      uses group-top;
    }

    container f {
      leaf with-ns { type tn:relative-ufnt; }
      leaf without-ns { type relative-ufnt; }
    }
  }
}
