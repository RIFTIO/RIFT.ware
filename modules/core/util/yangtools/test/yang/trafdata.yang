/*
 * STANDARD_RIFT_IO_COPYRIGHT
 *
 */

module trafdata {
  namespace "http://riftio.com/ns/riftware-1.0/rw-trafgen-data";
  prefix "trafdata";

  import ifmgr {
    prefix "ifmgr";
  }

  import rw-base-f {
    prefix "rwbase";
  }

  description "Test yang module";
  revision 2014-05-27 {
    description "Initial version"; 
  }
  
  augment /rwbase:colony/ifmgr:port-state {
    leaf freedata { 
      type string;
    }
  } 
}
