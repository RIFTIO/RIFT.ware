/*
 * STANDARD_RIFT_IO_COPYRIGHT
 *
 */

module rw-test-au2
{
  namespace "http://riftio.com/ns/riftware-1.0/rw-test-au2";
  prefix "test-au2";

  import rw-fpath-d {
    prefix rwfpath;
  }

  import rw-appmgr-d {
    prefix rwappmgr;
  }

  description "Dynamic schema merge test";
  revision 2014-05-27 {
    description "Initial version"; 
  }
}
