/*
 * STANDARD_RIFT_IO_COPYRIGHT
 *
 */

module rw-base-f {
  namespace "http://riftio.com/ns/riftware-1.0/rw-base";
  prefix "rwbase";

  import rw-pb-ext {
    prefix "rwpb";
  }

  description "Test yang module";
  revision 2014-05-27 {
    description "Initial version"; 
  }
  
  list colony {
    rwpb:msg-new Colony;
    key "name";

    leaf name {
      type string;
    } 
  }
}
