/* STANDARD_RIFT_IO_COPYRIGHT */

/**
 * @file rw-notify-ext.yang
 * @author Sameer Nayak
 * @date 2013/03/21
 * @brief RiftWare yang to protobuf conversion extensions
 */

module rw-notify-ext-d
{
  namespace "http://riftio.com/ns/riftware-1.0/rw-notify-ext";
  prefix "rwnotify";

  revision 2014-03-28 {
    description
      "Initial revision.";
    reference
      "RIFT yang extensions for converting yang files to Google
      Protocol Buffers (protobuf) using rift protoc-c extensions.";
  }
  extension log-event-id {
    argument "id";
    description
      "Generate logging meta-data, associated with the specified
      logging event ID.  Valid only on notification elements.  Allowed
      values are positive integers less than 4294967295.  IDs must be
      unique within a catagory.";
  }
  extension log-event {
    description
      "Indicates that this notification is a log event";
  }
  extension log-common {
    description
      "Indicates  this feild is common to all the log events and
      the autogen code will not create filters and fill routines.";
  }

  extension log-short-description {
    argument "description";
    description
      "When generating logging data in plain-text format, use the
      specified description as the base logging message, instead of the
      yang notification description.  This extension is typically used
      to produce a shorter message than the more detailed yang
      description, to ensure that length-limited logging outputs
      capture the most useful data.  Extra whitespace will be removed:
      all sequences of 1 or more whitespace characters will be
      converted to a single space in the output.  Leading and trailing
      whitespace will be removed.

      If this extension is not specified, then logging plain-text
      conversion will use the yang notification description (with extra
      whitespace removed) as the event description.";
  }

  extension field-text-format {
    argument "format";
    description
      "When generating logging data in plain-text format, convert the
      logging data using the specified sprintf-style format string,
      instead of the default format string.  Valid only on leaf, type,
      or typedef nodes.  The format will be processed depending on
      type, with the following call style:

        snprintf(buf, sz, format, leaf_value, leaf_name)

      The format may contain any POSIX format placeholder
      specification, particularly including the 'n$' parameter number
      syntax, which allows argument reordering.  The format must be
      valid; it may be validated at compile-time by an assertion in the
      generated code, although that should not be relied upon.

      If this extension is not specified, then the default format for a
      log-event plain text conversion is:

        LEAFNAME=LEAFVALUE

      where LEAFNAME is the name of the leaf in the original yang
      definition, and LEAFVALUE is the canonical XML string conversion
      of the leaf's value.  See RFC6020 for details.";
  }

  extension field-text-func {
    argument "c_function_name";
    description
      "When generating logging data in plain-text format, convert the
      element using the specified function.  Valid on any field in a
      log event, including fields that are converted to proto messages.
      Allowed values are valid C identifiers.

      The function must have the following C signature:
        ssize_t c_function_name(
          char* outbuf,
          size_t bufsz,
          const char* element_name,
          const TYPE* element_value)

      outbuf:
        The location to store field's text conversion.  No more than
        bufsz bytes may be written.  The function should append a
        terminating NUL character, so the actual text should consume no
        more than bufsz-1 bytes.
      bufsz:
        The size of outbuf, in bytes.
      element_name:
        The name of the element, as it appears in the yang leaf,
        container, or list definition.
      element_value:
        A pointer to the element value.  TYPE should be the same type
        as rift-protoc-c generates for the element.  It should not be
        void.  The TYPE may be validated at compile-time by static
        assertion, although that should not be relied upon.
      return:
        The function must return the numberof bytes added to the buffer
        (not including the terminating NUL), or a negative number if
        there is an error.  0 is a valid return value, which is
        equivalent to suppressing the output of the value.  The
        function must not return a value greater than bufsz.";
  }

/*
  extension tag-reserve {
    argument "value";
    description
      "Reserve space in the tag numbering for future expansion of the
      enclosing grouping, container, or choice.  Must be a positive
      decimal integer.  Choose carefully, as you cannot increase the
      value at a later time.";
  }
*/

} // rw-pb-ext
