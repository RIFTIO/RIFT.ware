/*
 * STANDARD_RIFT_IO_COPYRIGHT
 *
 */

module rw-test-au1
{
  namespace "http://riftio.com/ns/riftware-1.0/rw-test-au1";
  prefix "test-au1";

  import rw-fpath-d {
    prefix rwfpath;
  }

  import rw-vcs-d {
    prefix rw-vcs;
  }

  description "Dynamic schema merge test";
  revision 2014-10-01 {
    description "Initial version"; 
  }
}
