/*
 * STANDARD_RIFT_IO_COPYRIGHT
 *
 */

module rwvnffgd-d
{
  namespace "http://riftio.com/ns/riftware-1.0/rwvnffgd";
  prefix "rwvnffg";

  import rw-manifest-d {
    prefix "rwmani";
  }

  import rwvnfd-d {
    prefix "rwvnfd-d";
  }

  import rwvld-d {
    prefix "rwvld-d";
  }

  import rw-pb-ext {
    prefix "rwpb";
  }

  import rw-yang-types {
    prefix rwt;
  }

  import ietf-inet-types {
    prefix "inet";
  }

  import ietf-yang-types {
    prefix "yang";
  }

  revision 2015-04-22 {
    description
      "Initial revision. This YANG file defines 
       the VNF Forwarding Graph";
    reference
      "Derived from earlier versions of base YANG files";
  }

  container vnffgd {
    leaf id {
      description "ID of the VNF forwarding graph"; 
      type yang:uuid;
    }

    leaf vendor {
      description "Vendor.";
      type string;
    }

    leaf description {
      description "Description of the vnffgd.";
      type string;
    }

    leaf version {
      description "Version";
      type string;
    }

    leaf number-of-endpoints {
      description
          "Count of the external endpoints.";
      type uint32;
    }

    leaf number-of-virtual-links {
      description
          "Count of the virtual links.";
      type uint32;
    }

    list network-forwarding-path {
      description 
          "Describes a network forwarding path within vnffg.";
      key id;
      leaf id {
        description 
            "Specify the network forwarding path identifier.";
        type uint32;
      }
      leaf policy {
        description 
            "A policy rule to apply to the NFP";
        type string;
      }
    }

    list dependent-virtual-link {
      key vld-id;
      leaf vld-id {
        type leafref {
          path "/rwvld-d:vld/rwvld-d:vld-id";
        }
      }
    }

    list vnf-connection-points {
      key id;
      leaf id {
        type leafref {
          path "/rwvnfd-d:vnfd/rwvnfd-d:connection-points/rwvnfd-d:id";
        }
      }
    }

    list constituent-vnfs {
      key vnf-id;
      leaf vnf-id {
        type leafref {
          path "/rwvnfd-d:vnfd/rwvnfd-d:vnfd-id";
        }
      }
    }  
  }
}
