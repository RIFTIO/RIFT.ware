/* STANDARD_RIFT_IO_COPYRIGHT */

/**
 * @file rw-composite.yang
 * @author Vinod Kamalaraj
 * @date 2014/10/1
 * @brief A compsite YANG file that imports all other modules loaded by
 * rwuagent. This YANG file gives the uagent a global schema view
 */

module rw-composite-c
{
  namespace "http://riftio.com/ns/riftware-1.0/rw-composite";
  prefix "rwcomp";

  import rw-base-c
  {
    prefix "rw-base";
  }
  import rw-fpath-c
  {
    prefix "rw-fpath";
  }

  import rwuagent-cli-c
  {
     prefix "rwua";     
  }

  import rw-appmgr-c
  {
    prefix "rwappmgr";
  }

  import rwmanifest-c
  {
    prefix "rwmanifest";
  }

  import rw-vcs-c
  {
    prefix "rw-vcs";
  }
}
