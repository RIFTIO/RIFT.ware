/* STANDARD_RIFT_IO_COPYRIGHT */

/**
 * @file rwuagent-cli.yang
 * @author Tom Seidenberg
 * @date 2014/04/08
 * @brief Micro-agent test CLI.  Not for demo use!
 */

module other-rwuagent-cli
{
  namespace "http://riftio.com/ns/riftware-1.0/other-rwuagent-cli";
  prefix "rwua";

  import other-config_base { prefix config; }

  revision 2014-04-08 {
    description
      "Initial revision.";
  }

  augment /config:config {
    container uagent {
      description "Micro-agent actions";

      container forward {
        description "Forward some test data through the micro-agent";

        leaf data {
          description "The data to forward";
          type string;
        }
      }
    }
  }
} // module other-rwuagent-cli
