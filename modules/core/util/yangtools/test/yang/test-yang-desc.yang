/* STANDARD_RIFT_IO_COPYRIGHT */

/**
 * @file test-yang-desc.yang
 * @author Rajesh Velandy
 * @date 2014/05/26
 * @brief Top-level yang for testing libncx.
 */

module test-yang-desc
{
  namespace "http://riftio.com/ns/core/util/yangtools/tests/test-yang-desc";
  prefix "tyh";

  import rw-pb-ext { prefix "rwpb"; }

  description
    "Yang for testing yangpbc helper.";

  revision 2014-05-16 {
    description "Initial version";
  }


  container top1 {

    rwpb:msg-new Top1;
    container a1 {
      leaf a11 {
        type uint32;
      }
    }

    container b1 {
      leaf b11 {
        type uint32;
      }
    }

    container c1 {
      leaf c11 {
        type uint16;
      }
    }
  }
  container top2 {

    rwpb:msg-new Top2;
    container a2 {
      leaf a22 {
        type uint32;
      }
    }

    container b2 {
      leaf b22 {
        type uint32;
      }
    }

    container c2 {
      leaf c22 {
        type uint64;
      }
    }
  }
}
