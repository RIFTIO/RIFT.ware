/* STANDARD_RIFT_IO_COPYRIGHT */

/**
 * @file testncx-mod-base1.yang
 * @author Tom Seidenberg
 * @date 2014/03/25
 * @brief yangncx test file for modules
 */

module testncx-mod-base1
{
  namespace "http://riftio.com/ns/core/util/yangtools/tests/testncx-mod-base1";
  prefix "tnmb1";

  import testncx-mod-base3 { prefix "tnmb3-b1"; }

  description "Module testing for yangncx.";
  revision 2014-03-25 { description "Initial version"; }

  /////////////////////////////////////////////////////////////////////////////
  typedef b1t1 {
    type uint64;
    description "A typedef from base1";
  }

  typedef b1t2 {
    type tnmb3-b1:b3t1;
    description "A typedef of b3t1 from base3, in base2";
  }

  /////////////////////////////////////////////////////////////////////////////
  grouping b1g1 {
    leaf b1g1-b1t1 {
      description "A type b1t1 from group b1g1 in base1";
      type b1t1;
    }

    leaf b1g1-b1t2 {
      description "A type b1t2 from group b1g1 in base1";
      type b1t2;
    }

    leaf b1g1-n1 {
      description "A number from group b1g1 in base1";
      type int64;
    }

    leaf b1g1-s1 {
      description "A string from group b1g1 in base1";
      type string;
    }

    uses tnmb3-b1:b3g1;
  }

  /////////////////////////////////////////////////////////////////////////////
  container b1c1 {
    leaf b1c1-b1t1 {
      description "A type b1t1 from container b1c1 in base1";
      type b1t1;
    }

    leaf b1c1-b1t2 {
      description "A type b1t2 from container b1c1 in base1";
      type b1t2;
    }

    leaf b1c1-n1 {
      description "A number from container b1c1 in base1";
      type int64;
    }

    leaf b1c1-s1 {
      description "A string from container b1c1 in base1";
      type string;
    }

    uses tnmb3-b1:b3g1;
  }

  /////////////////////////////////////////////////////////////////////////////
  container b1c2 {
    uses b1g1;
  }
}
