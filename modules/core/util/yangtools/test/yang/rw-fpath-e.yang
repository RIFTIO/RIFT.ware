/*
 * STANDARD_RIFT_IO_COPYRIGHT
 *
 */

module rw-fpath-e
{
    namespace "http://riftio.com/ns/riftware-1.0/rw-fpath";
    prefix "rw-fpath";
  
    import rw-base-e {
        prefix rwbase;
    }

    import rw-cli-ext { 
        prefix "rwcli";
    }

    import rw-pb-ext {
        prefix "rwpb";
    }

    import rw-yang-types {
        prefix "rwt";
    }

    import rw-notify-ext {
        prefix "rwnotify";
    }

    import rw-log-e {
        prefix "rwlog";
    }

    revision 2014-03-31 {
        description
            "Initial revision.";
        reference
            "RIFT Trafgen Application";
    }

    rwpb:file-pbc-include "rwtypes.h";

    typedef flow-apply-method{
        type enumeration {
            enum loadbalance    {value 1;}
            enum exact-match    {value 2;}
            enum tunneling      {value 3;}
        }
    }
    
    typedef filter-type {
        type enumeration {
            enum trace    {value 1;}
            enum tcpdump  {value 2;}
            enum capture  {value 3;}
        }
    }
    typedef plugin-function-type {
        type enumeration {
            enum builtin { value 0; } 
            enum plugin-script { value 1; }
            enum none { value 2; }
        }
    }
    
    typedef interface-type{
        type enumeration{
            enum loopback {value 1;}
            enum fastpath-local {value 2;}
        }
    }
    
    typedef rwfpath-base-string {
        type string {
            length "1..256";
        }
    }
    typedef fast-slow{
        type enumeration{
            enum slow;
            enum fast;
        }
    }
    typedef up-down{
        type enumeration{
            enum down;
            enum up;
        }
    }
    typedef admin-state{
        type enumeration{
            enum down;
            enum up;
        }
    }
  
    typedef link-state{
        type enumeration{
            enum down;
            enum up;
        }
    }

    typedef lacp-state{
        type enumeration{
            enum down;
            enum up;
        }
    }
  
    typedef bundle-state-type{
        type enumeration{
            enum standby;
            enum active;
        }
    }

    typedef lacp-mode{
        type enumeration{
            enum none;
            enum passive;
            enum active;
        }
    }

    typedef lag-lb-mode{
        type enumeration{
            enum mac_ip;
            enum ip_trans;
            enum ip_trans_vsap;
        }
    }

    typedef lacp-rate{
        type enumeration{
            enum slow;
            enum fast;
        }
    }
  
    typedef mac-mode{
        type enumeration{
            enum active;
            enum follow;
            enum fixed;
        }
    }

    typedef yes-no{
        type enumeration {
            enum No;
            enum Yes;
        }
    }

    typedef on-off{
        type enumeration {
            enum Off;
            enum On;
        }
    }

    typedef ip-protocol-type {
        type enumeration {
            enum icmp { value 1; }
            enum tcp  { value 6; }
            enum udp  { value 17; }
            enum gre  { value 47; }
        }
    }
  
    typedef template-type {
        description "Types of templates that are configured on ports";
        type enumeration {
            enum single-template;
            enum range-template;
            enum sequence-template;
            enum pcap;
        }
    }
    typedef nexthoptype{
        type enumeration{
            enum none;
            enum local;
            enum connected;
            enum mac;
            enum tunnel;
            enum mpls;
            enum pool;
            enum nat_pool;
        }
    }
    typedef route-type{
        type enumeration{
            enum none;
            enum connected;
            enum local;
            enum static;
            enum pool;
            enum nat_pool;
        }
    }
    
  
    grouping ip-family{
        list neighbor{
            rwpb:msg-new IpNeighInfo;
            key "ip-address lport-id";
            leaf ip-address{
                rwpb:field-inline "true";
                rwpb:field-string-max 46;
                type rwt:ip-address;
            }
            leaf lport-id{
                type uint32;
            }
            leaf mac{
                rwpb:field-inline "true";
                type rwt:mac-address;
                rwpb:field-string-max 18;    
            }
        }
        list route {
            max-elements 32;
            rwpb:msg-new IpRouteInfo;
            key "prefix";
          
            leaf prefix {
                description "IP prefix for the route";
                type rwt:ip-prefix-non-canonical;
                rwpb:field-string-max 64;
                rwpb:field-inline "true";
            }
            leaf type{
                type route-type;
            }
            leaf nexthop-index{
                description "Nexthop handle index";
                type uint32;
            }
            leaf nexthop-context-id{
                type uint32;
            }
            //uses ip-nexthops;
        }
    }
    grouping vrf-info{
        list nexthop-handle{
            key "nexthop-index nexthop-nc-id";
            
            leaf nexthop-index{
                type uint32;
            }
            leaf nexthop-nc-id{
                type uint32;
            }
            list nexthops{
                rwpb:field-inline "true";
                max-elements 16;
                key "nexthop-type lport-id";
                
                leaf nexthop-type{
                    description "Type of the nexthop";
                    type nexthoptype;
                }
                leaf lport-id{
                    description "Ifindex of the nexthop";
                    type uint32;
                }
                leaf gateway{
                    description "Gateway Address of the nexthop";
                    type rwt:ip-address;
                    rwpb:field-string-max 46;
                    rwpb:field-inline "true";
                }
                leaf interface_name{
                    description "Interface Name of the nexthop";
                    type string;
                    rwpb:field-string-max 64;
                    rwpb:field-inline "true";
                }
            }
            
        }
        container ipv4{
            rwpb:msg-new Ipv4Info;
            uses ip-family;
        }
        container ipv6{
            rwpb:msg-new Ipv6Info;
            uses ip-family;
        }
    }
    
    /* Imported from the data files */
    grouping rx-queue-stats {
        leaf rx-qid {
            type uint32;
            description "Receive Queue Id";
        }
        leaf rx-rate-pps {
            type rwt:gauge32;
            description "Rx Rate(pps)";
        }
        leaf rx-rate-mbps {
            type rwt:gauge32;
            description "Rx Rate(Mbps)";
        }
        leaf input-packets {
            type rwt:zero-based-counter64;
            description "Input packets";
        }
        leaf input-bytes-MB {
            type rwt:zero-based-counter64;
            description "Total In bytes(MB)";
        }
    }

    grouping tx-queue-stats {
        leaf tx-qid {
            type uint32;
            description "Receive Queue Id";
        }
        leaf tx-rate-pps {
            type rwt:gauge32;
            description "Tx Rate(pps)";
        }
        leaf tx-rate-mbps {
            type rwt:gauge32;
            description "Tx Rate(Mbps)";
        }
        leaf output-errors {
            type rwt:zero-based-counter32;
            description "Output Errors";
        }
        leaf output-packets {
            type rwt:zero-based-counter64;
            description "Output packets";
        }
        leaf output-bytes-MB {
            type rwt:zero-based-counter64;
            description "Total Out Bytes(MB)";
        }
    }
    grouping ip-config-family{
        list route {
            description "static IPv4 route configured";
            rwpb:msg-new ConfigRoute;
            rwpb:msg-flat true;
            rwpb:field-inline-max "yang";
            
            max-elements 32;
            
            key "prefix";
            
            leaf prefix {
                description "static IPv4 route prefix";
                type rwt:ip-prefix-non-canonical;
                rwpb:field-string-max 64;
            }
            list nexthop {
                rwpb:msg-flat true;
                rwpb:field-inline-max "yang";
                rwpb:msg-new ConfigNexthop;
                
                max-elements 10;
                
                key "gateway interface-name";
                leaf gateway {
                    description "gateway address of the static route";
                    type rwt:ip-address;
                    rwpb:field-string-max 46;
                }
                leaf interface-name {
                    description "interface of the static route";
                    type string;
                    rwpb:field-inline "true";
                    rwpb:field-string-max 64;
                }
            }
        }
        list neighbor {
            rwpb:msg-new ConfigArp;
            rwpb:msg-flat true;
            rwpb:field-inline-max "yang";
            
            max-elements 32;
            
            key "address";
            
            leaf address{
                description "IPv4 address for the static arp entry";
                type rwt:ip-address;
                rwpb:field-string-max 46;
            }
            leaf macaddress {
                description "MAC address for the static arp entry";
                type rwt:mac-address;
                rwpb:field-string-max 17;
            }
            leaf interface-name {
                description "Interface Name for the static arp entry";
                type string;
                rwpb:field-string-max 64;
            }
        }
        list pool{
            rwpb:msg-new ConfigPool;
            rwpb:msg-flat true;
            rwpb:field-inline-max "yang";
            rwcli:new-mode "ip-pool";
            
            max-elements 32;
            
            key "name";
            
            leaf name{
                description "pool name for the pool";
                type string;
                rwpb:field-string-max 64;
            }
            list address{
                rwpb:msg-flat true;
                rwpb:field-inline-max "yang";
                max-elements 10;
                rwpb:msg-new ConfigPoolAddress;
                key "prefix";
                leaf prefix {
                    description "prefix for the pool";
                    type rwt:ip-prefix-non-canonical;
                    rwpb:field-string-max 64;
                }
            }
        }
        list nat-pool {
            rwpb:msg-new ConfigNatPool;
            rwpb:msg-flat true;
            rwpb:field-inline-max "yang";
            rwcli:new-mode "ip-nat-pool";  
            max-elements 32;
            
            key "name";
            
            leaf name{
                description "pool name for the nat-pool";
                type string;
                rwpb:field-string-max 64;
            }
            list address{
                rwpb:msg-flat true;
                rwpb:field-inline-max "yang";
                rwpb:msg-new ConfigNatPoolAddress;
                max-elements 10;
                key "prefix";
                leaf prefix {
                    description "prefix for the nat-pool";
                    type rwt:ip-prefix-non-canonical;
                    rwpb:field-string-max 64;
                }
            }
        }
    }
    grouping reassembly-stats{
        container reassembly-stats {
            rwpb:msg-new ReassemblyStats;
            rwpb:msg-flat true;
            list work{
                rwpb:field-inline-max "yang";
                max-elements 10;
                key "id";
                leaf id{
                    description "reassembly work-id";
                    type uint32;
                }
                leaf total-fragments-received{
                    description "Total number of ipv4/ipv6 fragments(mbufs) received";
                    type rwt:zero-based-counter64;
                }
                leaf total-packets-reassembled{
                    description "Total number of ipv4/ipv6 fragments reassembled";
                    type rwt:zero-based-counter64;
                }
                leaf total-fragments-timedout-errors{
                    description "Total number of ipv4/ipv6 fragments timedout/errors";
                    type rwt:zero-based-counter64;
                }
                leaf total-fragments-nospace{
                    description "Total number of ipv4/ipv6 fragments dropped due to nospace";
                    type rwt:zero-based-counter64;
                }
                leaf total-fragments-rngsize{
                    description "Total number of ipv4/ipv6 fragments dropped due to rngspace";
                    type rwt:zero-based-counter64;
                }
                leaf total-fragments-addfailed{
                    description "Total number of ipv4/ipv6 fragments dropped due to add failures";
                    type rwt:zero-based-counter64;
                }
                leaf total-insert-fragments{
                    description "Total number of fragments attempted to be inserted/found";
                    type rwt:zero-based-counter64;
                }
                leaf total-add-packets{
                    description "Total number of fragments add operations";
                    type rwt:zero-based-counter64;
                }
                leaf total-delete-packets{
                    description "Total number of fragments delete operations";
                    type rwt:zero-based-counter64;
                }
                leaf total-reuse-packets{
                    description "Total number of fragments reused";
                    type rwt:zero-based-counter64;
                }
                leaf total-outstanding-packets{
                    description "Total outstanding unique fragments waiting";
                    type rwt:zero-based-counter64;
                }
                leaf total-invalid-packets{
                    description "Total invalid fragments";
                    type rwt:zero-based-counter64;
                }
                leaf total-ooo-packets{
                    description "Total Out of Order fragments";
                    type rwt:zero-based-counter64;
                }
                leaf total-explicitstale-packets{
                    description "Total packets deleted with explicit stale checking";
                    type rwt:zero-based-counter64;
                }
                leaf tbl-alloc-entries{
                    type rwt:zero-based-counter64;
                }
                leaf tbl-free-entries{
                    type rwt:zero-based-counter64;
                }
                leaf tbl-stale-entries{
                    type rwt:zero-based-counter64;
                }
                leaf tbl-used-entries{
                    type rwt:zero-based-counter64;
                }
                leaf tbl-frags{
                    type rwt:zero-based-counter64;
                }
            }
        }
    }
    
    grouping kernel-stats{
        container kernel-stats{
            rwpb:msg-new KernelKniStats;
            rwpb:msg-flat true;
          
            list device{
                rwpb:field-inline-max "yang";
                max-elements 128;
              
                key "name";
                leaf name{
                    rwpb:field-string-max 16;
                    type string;  
                }
                leaf ifindex{
                    description "Kernel ifindex of the device\n";
                    type uint32;
                }
              
                leaf rx-packets{
                    description "Number of packets recevied by the kernel from fastpath\n";
                    type uint64;
                }
              
                leaf rx-as-tx-packets{
                    description "Number of packets recevied by the kernel from fastpath in egress direction with respect to fastpath (application->fastpath)\n";
                    type uint64;
                }
                leaf rx-as-tx-filtered{
                    description "Number of packets received by the kernel in egress direction which are dropped (not delivered to kernel network stack)";
                    type uint64;
                }
                leaf rx-as-tx-delivered{
                    description "Number of packets received by the kernel in egress direction which are delivered to kernel network stack)";
                    type uint64;
                }
                leaf rx-only-packets{
                    description "Number of packets received by the kernel from fastpath in ingress direction";
                    type uint64;
                }
                leaf rx-only-filtered{
                    description "Number of packets received by the kernel from fastpath in ingress direction but dropped before delivering to network stack";
                    type uint64;
                }
                leaf rx-only-delivered{
                    description "Number of packets received by the kernel from fastpath in ingress direction delivered to network stack";
                    type uint64;
                }
                leaf rx-dropped{
                    description "Number of packets received by the kernel from fastpath but dropped (lack of skb)";
                    type uint64;
                }
                leaf rx-drop-noroute{
                    description "number of packets dropped in the kernel due to failure in policy forwarding";
                    type uint64;
                }
                leaf tx-packets{
                    description "Number of packets sent by the kernel to fastpath";
                    type uint64;
                }
              
                leaf tx-dropped{
                    description "Number of packets dropped by the kernel when sending to fastpath";
                    type uint64;
                }
                leaf tx-no-txq{
                    description "Number of packets dropped by kernel due to lack of txq space(slow reader fastpath)";
                    type uint64;
                }
                leaf tx-no-allocq{
                    description "Number of packets dropped by kernel due to lack of allocq";
                    type uint64;
                }
                leaf tx-enq-fail{
                    description "Number of packets dropped by kernel due to enqueue fail";
                    type uint64;
                }
                leaf tx-deq-fail{
                    description "Number of packets dropped by kernel due to dequeue fail";
                    type uint64;
                }
            }
        }
    }
        
        grouping ip-endpoint {
        choice endpoint-address {
            case ip-addr {
                leaf address {
                    type rwt:ip-address;
                    rwpb:field-string-max 46;
                }
            }
            case d-name {
                leaf domain-name {
                    type string;
                    rwpb:field-string-max 128;
                }
            }
        }
        leaf ip-proto {
            type enumeration {
                enum proto-tcp  { value 6; }
                enum proto-udp { value 17; }
            }
        }
        leaf port {
            type uint16;
        }
    }

    grouping gre-ip-endpoint {
       list endpoint {
           rwpb:field-inline-max "yang";
           max-elements 16;
           rwpb:field-inline "true";
           key "address";

           leaf address {
               type rwt:ip-address;
               rwpb:field-string-max 46;
           }
       }
    }                                     



    grouping script {
        leaf script-name {
            type string;
            rwpb:field-string-max 64;
        }
    }


    grouping receive-function-info {
        leaf function-type  {
            type plugin-function-type;
        }
        container builtin {
            choice builtin-types  {
                case basiclb {
                    container basic-lb {
                        uses ip-endpoint;
                    }
                }
                case softgredpath {
                    container soft-gre-dpath {
                        uses gre-ip-endpoint;
                        leaf ipsec {
                          type on-off;
                        }
                    }
                }
            }
        }
    }

    grouping classify-function-info {
        leaf function-type  {
            type plugin-function-type;
        }
        container builtin {
            choice builtin-types { 
                case basiclb {
                    container basic-lb {
                        leaf key-type {
                            type enumeration {
                                enum basic-5tuple { value 1; }
                            }
                        }
                    }
                }
                case softgredpath {
                    container soft-gre-dpath {
                        leaf gre-key-type {
                            type enumeration {
                                enum  source-mac-based { value 1; }
                            }
                        }
                    }
                }
            }
        }
    }

    grouping server-selection-function-info {
        list server-group {
            //rwpb:msg-new ServerGroups;
            rwpb:msg-flat true;
            rwpb:field-inline "true";
            rwpb:field-inline-max "yang";
            //rwcli:new-mode "server-group";

            max-elements 4;

            key "name";

            leaf name {
                description "server group name";
                type string;
                rwpb:field-string-max 32;
            }
            list server {
                rwpb:field-inline-max "yang";
                max-elements 4;
                rwpb:field-inline "true";
                rwpb:field-inline-max "yang";
                key "address";

                leaf address {
                    description "server address";
                    type rwt:ip-address;
                    rwpb:field-string-max 46;
                }
                leaf port {
                    type uint16;
                }
            }
            container nat-address {
                leaf src-address {
                    description "server address";
                    type rwt:ip-address;
                    rwpb:field-string-max 46;
                }
                leaf src-port {
                    type uint16;
                }
                leaf network-context {
                    type string;
                    rwpb:field-string-max 64;
                }
            }
        }
        leaf function-type  {
            type plugin-function-type;
        }
        container builtin {
            choice builtin-types {
                case basiclb {
                    container basic-lb {
                        leaf selection-type {
                            type enumeration {
                                enum basic-round-robin  { value 1; }
                                enum weighted       { value 2; }
                            }
                        }
                    }
                }
            }
        }

        container selection-criteria {
            rwpb:msg-new SelectionCriteria;
            choice proto-specific {
                // This should come from augmentation - TBD
                case proto-specific-dns {
                    container dns-lb {
                        rwcli:new-mode "selection-dns-lb";
                        list match-rule {
                            rwpb:field-inline-max "yang";
                            max-elements 4;
                            rwpb:field-inline "true";
                            rwpb:field-inline-max "yang";
                            key "priority";
                            leaf priority {
                                type uint32;
                            }
                            leaf domain {
                                description "domain name";
                                type string;
                                rwpb:field-string-max 64;
                            }
                            leaf server-group {
                                description "server groupname";
                                type string;
                                rwpb:field-string-max 64;
                            }
                        }                                      
                    }
                }
                case proto-specific-radius {
                    container radius-lb {
                        rwcli:new-mode "selection-radius-lb";
                        list match-rule {
                            rwpb:field-inline-max "yang";
                            max-elements 4;
                            rwpb:field-inline "true";
                            rwpb:field-inline-max "yang";
                            key "priority";
                            leaf priority {
                                type uint32;
                            }
                            leaf domain {
                                description "domain name";
                                type string;
                                rwpb:field-string-max 64;
                            }
                            leaf server-group {
                                description "server groupname";
                                type string;
                                rwpb:field-string-max 64;
                            }
                        }                                      
                    }
                }

            }
        }
    }
   
    
        grouping transform-function-info {
        leaf function-type  {
            type plugin-function-type;
        }
        container builtin {
            choice builtin-types {
                case basictransfform {
                    container basic-transform {
                        leaf transform-type {             
                            type enumeration {
                                enum destination-nat  { value 1; }
                                enum double-nat       { value 2; }
                            }
                        }
                    }
                }
                case softgretransform {
                    container soft-gre-dpath {
                        leaf gre-transform-type {
                            type enumeration {
                                enum inner-src-nat   { value 1; }
                                enum soft-gre-tunnel { value 2; }
                            }
                        }
                       list nat-address {
                          rwpb:field-inline-max "yang";
                          max-elements 16;                                                                                                                                                          
                          rwpb:field-inline "true";
                          key "src-address";

                         leaf src-address {
                           description "nat src address";
                           type rwt:ip-address;
                           rwpb:field-string-max 46;
                         }
                         leaf src-port {
                            type uint16;
                         }
                         leaf network-context {
                            type string;
                            rwpb:field-string-max 64;
                          }
                       }
                       list gre-address {
                          rwpb:field-inline-max "yang";
                          max-elements 16;                                                                                                                                                          
                          rwpb:field-inline "true";
                          key "src-address";
                          leaf src-address {       
                           description "nat src address";
                           type rwt:ip-address;
                           rwpb:field-string-max 46;
                          }
                          leaf dst-address {
                           description "nat dst address";
                           type rwt:ip-address;
                           rwpb:field-string-max 46;
                          }
                          leaf network-context {
                            type string;
                            rwpb:field-string-max 64;
                          }
                       }
                       leaf ipsec {
                         type on-off;
                       }
                    }
                }
            }
        }
    }


    grouping bind-interface {
        container bind {
            rwpb:field-inline "true";
            choice port-type {
                case port {
                    leaf port {
                        description "port name to bind the interface to";
                        rwpb:field-string-max 64;
                        type string;
                        rwpb:field-inline "true";
                    }
                }
                case bundle{
                    leaf bundle-ether{
                        description "Name of the port";
                        rwpb:field-inline "true";
                        rwpb:field-string-max 64;
                        type string;
                    }
                }
            }
            leaf vlan{
                description "vlan tag of the port to which the interface is bound";
                type uint16;    
            }
        }
    }
    
    grouping ipdomain{
        //rwpb:msg-new ConfigIpDomain;
        list interface {
            rwpb:msg-new ConfigIpInterface;
            rwpb:msg-flat true;
            rwpb:field-inline-max "yang";
            rwcli:new-mode "ip-interface";
          
            max-elements 32;
          
            key "name";
          
            leaf name {
                description "interface name";
                type string;
                rwpb:field-string-max 64;
                rwpb:field-inline "true";
            }
            leaf interface-type{
                description "Interface type. defaults to an interface bound to port/vlan";
                type interface-type;
            }
            list ip {
                rwpb:field-inline-max "yang";
                max-elements 32;
                key "address";
                  
                leaf address {
                    description "ipv4 address assigned to the interface";
                    type rwt:ipv4-prefix-non-canonical;
                    rwpb:field-string-max 18;
                    rwpb:field-inline "true";
                }
            }
            list ipv6 {
                rwpb:field-inline-max "yang";
                max-elements 32;
                key "address";
                  
                leaf address {
                    description "ipv6 address assigned to the interface";
                    type rwt:ipv6-prefix-non-canonical;
                    rwpb:field-string-max 64;
                    rwpb:field-inline "true";
                }
            }
            uses bind-interface;
        }
        
        container ip {
            rwpb:msg-new ConfigIp;
            rwpb:msg-flat true;
            uses ip-config-family;
        }
        container ipv6 {
            rwpb:msg-new ConfigIpv6;
            rwpb:msg-flat true;
            leaf forwarding{
                type empty;
            }
            uses ip-config-family;
        }
    }
    /*
      |       +-- rw protocol
      |       +-- rw destination-mac (..)
      |       +-- rw source-ip (...)
      |       +-- rw destination-ip(...)
      |       +-- rw source-port (...)
      |       +-- rw destination-port (...)
      |       +-- rw packet-size(...)
    */
    grouping range-param-attr {    
        leaf protocol{
            type ip-protocol-type;
        }
      
        container destination-mac {
            leaf start {
                type rwt:mac-address;
                rwpb:field-string-max 18;
            }
            leaf minimum {
                type rwt:mac-address;
                rwpb:field-string-max 18;
            }
            leaf maximum {
                type rwt:mac-address;
                rwpb:field-string-max 18;
            }
            leaf increment {
                type uint16;
            }
            container dynamic{
                leaf gateway{
                    description "Gateway IP address";
                    type rwt:ip-address;
                    rwpb:field-string-max 46;
                }
            }
        }
      
        container source-ip {
            leaf start {
                description "Starting source IP address";
                type rwt:ip-address;
                rwpb:field-string-max 46;
            }
            leaf minimum {
                description "Minimum source IP address";
                type rwt:ip-address;
                rwpb:field-string-max 46;
            }
            leaf maximum {
                description "Maximum source IP address";
                type rwt:ip-address;
                rwpb:field-string-max 46;
            }
            leaf increment {
                type uint16;
            }
        }
      
        container destination-ip {
            leaf start {
                description "Starting destination IP address";
                type rwt:ip-address;
                rwpb:field-string-max 46;
            }
            leaf minimum {
                description "Minimum destination IP address";
                type rwt:ip-address;
                rwpb:field-string-max 46;
            }
            leaf maximum {
                description "Maximum destination IP address";
                type rwt:ip-address;
                rwpb:field-string-max 46;
            }
            leaf increment {
                type uint16;
            }
        }
      
        container source-port {
            leaf start {
                type rwt:port-number;
            }
            leaf minimum {
                type rwt:port-number;
            }
            leaf maximum {
                type rwt:port-number;
            }
            leaf increment {
                type uint16;
            }
        }
      
        container destination-port {
            leaf start {
                type rwt:port-number;
            }
            leaf minimum {
                type rwt:port-number;
            }
            leaf maximum {
                type rwt:port-number;
            }
            leaf increment {
                type uint16;
            }
        }
      
        container packet-size {
            leaf start {
                type uint16;
            }
            leaf minimum {
                type uint16;
            }
            leaf maximum {
                type uint16;
            }
            leaf increment {
                type uint16;
            }
        }
        leaf num-fragments {
            description "Total number of fragments for each packet";
            type uint32;
        }

        container inner-source-ip {
            leaf start {
                description "Starting source IP address";
                type rwt:ip-address;
                rwpb:field-string-max 46;
            }
            leaf minimum {
                description "Minimum source IP address";
                type rwt:ip-address;
                rwpb:field-string-max 46;
            }
            leaf maximum {
                description "Maximum source IP address";
                type rwt:ip-address;
                rwpb:field-string-max 46;
            }
            leaf increment {
                type uint16;
            }
        }

        container inner-destination-ip {
            leaf start {
                description "Starting destination IP address";
                type rwt:ip-address;
                rwpb:field-string-max 46;
            }
            leaf minimum {
                description "Minimum destination IP address";
                type rwt:ip-address;
                rwpb:field-string-max 46;
            }
            leaf maximum {
                description "Maximum destination IP address";
                type rwt:ip-address;
                rwpb:field-string-max 46;
            }
            leaf increment {
                type uint16;
            }
        }

        container inner-source-port {
            leaf start {
                type uint16;
            }
            leaf minimum {
                type uint16;
            }
            leaf maximum {
                type uint16;
            }
            leaf increment {
                type uint16;
            }
        }
      
        container inner-destination-port {
            leaf start {
                type uint16;
            }
            leaf minimum {
                type uint16;
            }
            leaf maximum {
                type uint16;
            }
            leaf increment {
                type uint16;
            }
        }
    }

    /*
      |       +-- rw protocol
      |       +-- rw destination-mac 
      |       +-- rw source-ip 
      |       +-- rw destination-ip
      |       +-- rw source-port 
      |       +-- rw destination-port 
      |       +-- rw packet-size
    */
    grouping template-attr {
        leaf protocol{
            type ip-protocol-type;
        }
        leaf packet-size {
            description "Size of packet to be generated";
            type uint32;
        }
        leaf num-fragments {
            description "Total number of fragments for each packet";
            type uint32;
        }
        leaf source-port {
            description "IP L4 Source Port of the generated packet";
            type uint16;
        }
        leaf destination-port {
            description "IP L4 Destination Port of the generated packet";
            type uint16;
        }
        leaf destination-ip{
            description "destination ip address of the generated packet";
            type rwt:ip-address;
            rwpb:field-string-max 46;
        }
        leaf source-ip{
            description "source ip address of the generated packet";
            type rwt:ip-prefix-non-canonical;
            rwpb:field-string-max 64;
        }
        container destination-mac{
            container dynamic{
                leaf gateway{
                    description "Gateway IP Address";
                    type rwt:ip-address;
                    rwpb:field-string-max 46;
                }
            }
            leaf mac{
                rwpb:field-string-max 18;
                type rwt:mac-address;
            }
        }
        leaf inner-destination-ip{                                                                                                                                                        
            description "inner-destination ip address of the generated packet";
            type rwt:ip-address;
            rwpb:field-string-max 46;
        }
        leaf inner-source-ip{
            description "inner-source ip address of the generated packet";
            type rwt:ip-prefix-non-canonical;
            rwpb:field-string-max 64;
        }
        leaf inner-source-port {
            description "IP L4 Source Port of the generated packet";
            type uint16;
        }
        leaf inner-destination-port {
            description "IP L4 Destination Port of the generated packet";
            type uint16;
        }
    }
  
    grouping transmit-param-attr {
        leaf descr-string {
            description "description comment for trafgen";
            rwpb:field-string-max 32;
            type string;
        }

        leaf tx-rate {
            description "Transmit rate as percentage of port speed";
            type uint32;
        }
        leaf packet-count {
            description 
                "Total number of packets to be generated(default to unlimited)";
            type uint32;
        }
        leaf burst-size {
            description "Burst size  in no of packets be generated";
            type uint32;
        }
        leaf tx-cycles {
            description "transmit cycle of the gernated traffic";
            type uint32;
        }

        container transmit-mode {
            description
                "Transmit mode for the packets to be sent. It can be
        single|range|sequence|pcap <file>. In single mode, the same packet
        will be sent out continuously. In the range mode, depending on the
        params configured, the destination-ip, sourceip, sourceport,
        destination-port will keep getting changed. In the sequence mode,
        you can enter as many as 16 sequences of packets that need to be sent
        continuously. Pcap mode needs a filename. The file is parsed to get
        the packets and these packets are sent out.";
            leaf single {
                type empty;
            }
            leaf range {
                type empty;
            }
            leaf sequence {
                type empty;
            }
            container pcap {
                leaf file{
                    rwpb:field-string-max 256;
                    type string;
                }
            }
        }
        leaf packet-content-script {
            type string;
            rwpb:field-string-max 64;
        }
        leaf timestamp-packets {
            description "timestamp packets for latency measurement";
            type on-off;
        }
    }

    grouping lacppdu-info{
        rwpb:msg-new LacppduInfo;
        leaf systemid {
            description "System-d of the actor";
            type rwt:mac-address;
            rwpb:field-string-max 17;
        }
        leaf systemprio{
            type uint32;
        }
        leaf key{
            type uint32;
            description "actor key";
        }
        leaf portid{
            type uint32;
            description "actor portid";
        }
        leaf portprio{
            type uint32;
        }
        /*
          leaf state{
          type bits {
          bit aggregate {
          position 0;
          }
          bit timeout {
          position 1;
          }
          bit sync {
          position 2;
          }
          bit collecting {
          position 3;
          }
          bit distributing {
          position 4;
          }
          bit defaulted {
          position 5;
          }
          bit expired {
          position 6;
          }
          }
          rwpb:field-string-max 8;
          }
        */
        container state{
            leaf activity{
                type uint32;
            }
            leaf aggregate{
                type uint32;
            }
            leaf timeout {
                type uint32;
            }
            leaf sync {
                type uint32;
            }
            leaf collecting {
                type uint32;
            }
            leaf distributing {
                type uint32;
            }
            leaf defaulted {
                type uint32;
            }
            leaf expired {
                type uint32;
            }
        }
    }
    grouping port-virtual-fabric {
        container virtual-fabric {
            rwcli:new-mode "  virtual-fabric";
            leaf fabric{
                type on-off;
            }
        }
    }
    grouping vlan-grouping{
        list vlan{
            key "id";
            rwcli:new-mode "  vlan";
            rwpb:field-inline-max yang;
            max-elements 32;

            leaf id {
                type uint32;
            }
            leaf descr-string {
                description "description comment for port";
                rwpb:field-inline "true";
                rwpb:field-string-max 32;
                type string;
            }
          
            leaf open {
                description "open the specified port";
                type empty;
            }
          
            leaf shutdown {
                description "Administrative shutdown of the port";
                type empty;
            }
            uses port-virtual-fabric;
        }
    }
    grouping flow-control{
        container flow-control {
            leaf flow-type {
                description "none|rx|tx|both";
                type string;
                rwpb:field-inline "true";
                rwpb:field-string-max 5;
            }
            leaf high-watermark {
                type uint32;
            }
            leaf low-watermark {
                type uint32;
            }
            leaf pause-time {
                type uint32;
            }
            leaf send-xon {
                description 
                    "whether or no to send XON, when flow control status change 
              to no flow control";
                type on-off;
            }
        }
    }
  

    grouping  ip-flows-list {
        list flows {
            rwpb:field-inline-max yang;
            max-elements 256;
            
            key "flow-id";
            
            leaf flow-id {
                type uint64;
                description "Flow Id";
            }
            leaf install-state {
                type enumeration {
                    enum local { value 0; }
                    enum remote  { value 1; }
                    enum remote-pending  { value 2; }
                }
            }
            leaf flow-type {
                type uint32;
            } 
            leaf vsapid {
                type uint32;
            }
            leaf appdata {
                type uint32;
            }
            leaf ncid {
                type uint32;
            }
            leaf port-meta {
                type uint32;
            }
            leaf ip-version {
                type uint8;
            }
            leaf ip-protocol {
                type uint8;
            }
            leaf ip-src-address {
                type rwt:ip-address;                                                
                rwpb:field-string-max 46;
                rwpb:field-inline "true";
            }
            leaf ip-dst-address {
                type rwt:ip-address;                                                
                rwpb:field-string-max 46;
                rwpb:field-inline "true";
            }
            leaf ip-src-port {
                type uint16;
            }
            leaf ip-dst-port {
                type uint16;
            }
            leaf gre-proto {
                type uint16;
            }
            leaf gre-key {
                type uint32;
            }
            leaf in-src-mac {
                type rwt:mac-address;
                rwpb:field-string-max 17;
            }
            leaf in-dst-mac {
                type rwt:mac-address;
                rwpb:field-string-max 17;
            }
            leaf in-eth-proto {
                type uint16;
            }
            leaf in-eth-vlan-id {
                type uint16;
            }
            leaf in-ip-src-address {
                type rwt:ip-address;                                                
                rwpb:field-string-max 46;
                rwpb:field-inline "true";
            }
            leaf in-ip-dst-address {
                type rwt:ip-address;                                                
                rwpb:field-string-max 46;
                rwpb:field-inline "true";
            }
            leaf esp-spi {
                type uint32;
            }
        }
    }


// Scriptable-LB related - to be moved out

    grouping slb-session-info {
        container slb-session {
            leaf ncid {
                type uint32;
            }
            choice sess-types {
                case info-session {
                    container info {
                        leaf src-addr {                                                                                                                         
                            type uint32;
                        }
                        leaf dst-addr {
                            type uint32;
                        }
                        leaf src-address {
                            type rwt:ip-address;                                                
                            rwpb:field-string-max 46;
                            rwpb:field-inline "true";
                        }
                        leaf dst-address {
                            type rwt:ip-address;                                                
                            rwpb:field-string-max 46;
                            rwpb:field-inline "true";
                        }
                        leaf proto {
                            type uint8;
                        }
                        leaf src-port {
                            type uint16;
                        }
                        leaf dst-port {
                            type uint16;
                        }
                        leaf gre-proto {
                            type uint16;
                        }
                        leaf inner-eth-src-addr {
                           type rwt:mac-address;
                           rwpb:field-string-max 18;
                        }
                        leaf inner-eth-dst-addr {
                           type rwt:mac-address;
                           rwpb:field-string-max 18;
                        }
                        leaf inner-eth-proto {
                            type uint16;
                        }
                        leaf inner-eth-vlan {
                            type uint16;
                        }
                        leaf receive-ipsec {
                            type uint8;
                        }
                        leaf transform-ipsec {
                            type uint8;
                        }
                    }
                    container proto-specific {
                        leaf proto-info {
                            type binary {
                                length "1..64";
                            }
                        }
                    }
                }
            }
        }
    }


    notification fastpath_packet_trace {
        rwnotify:log-event-id 00001003;
        description "Packet trace";
        uses rwlog:severity-error;
        uses rwlog:packet-info;

        leaf packet-data { type binary; }
    }

    augment /rwbase:colony {
        // Work around for Jira: 1879
        list bundle-ether {
            rwcli:new-mode " bundle-ether";
            key "name";
            rwpb:field-inline-max yang;
            max-elements 32;
      
            leaf name {
                description "Name of the bundle";
                rwpb:field-inline "true";
                rwpb:field-string-max 64;
                type string;
            }

            leaf descr-string {
                description "description comment for port";
                rwpb:field-inline "true";
                rwpb:field-string-max 32;
                type string;
            }

            leaf open {
                description "open the specified port";
                type empty;
            }
            leaf mtu{
                description "MTU of the port";
                type uint32;
            }
            leaf shutdown {
                description "Administrative shutdown of the port";
                type empty;
            }
            uses port-virtual-fabric;
            container lacp{
                container system{
                    leaf priority{
                        description "configure the lacp priority for the system(colony)";
                        type uint32;
                    }
                    leaf mac{
                        description "MAC address used by the Link Aggregation Group";
                        type rwt:mac-address;
                        rwpb:field-string-max 18;    
                    }
                }
            }
            container bundle{
                container minimum-active{
                    leaf links{
                        description "Minimum number of active links to bring up the bundle";
                        type uint32;
                    }
                }
                container maximum-active{
                    leaf links{
                        description "Maximum number of active links in the bundle";
                        type uint32;
                    }
                }
                leaf load-balance{
                    description "packet contents to use for load-balancing";
                    type lag-lb-mode;
                }
                leaf mac-mode{
                    description "Mac-mode for 1:1 redundancy";
                    type mac-mode;
                }
            }
            uses vlan-grouping;
        }

        list port {
            rwcli:new-mode " port";
            key "name";
            rwpb:field-inline-max yang;
            max-elements 32;

            leaf name {
                description "Name of the port";
                rwpb:field-inline "true";
                rwpb:field-string-max 64;
                type string;
            }

            leaf descr-string {
                description "description comment for port";
                rwpb:field-inline "true";
                rwpb:field-string-max 32;
                type string;
            }
            uses port-virtual-fabric;
            container open {
                description "open the specified port";
                container application{
                    description "Application that is using this port. Default is IPFP";
                    container ip-fastpath {
                        presence true;
                        leaf virtual-fabric {
                            type empty;
                        }
                    }
                    leaf trafgen {
                        type empty;
                    }  
                }
            }
            leaf mtu{
                description "MTU of the port";
                type uint32;
            }
            leaf shutdown {
                description "Administrative shutdown of the port";
                type empty;
            }
            choice member-mode{
                case bundled{
                    container bundle{
                        leaf name{
                            description "Name of the port";
                            rwpb:field-inline "true";
                            rwpb:field-string-max 64;
                            type string;
                        }
                        leaf mode{
                            type lacp-mode;
                        }
                        container port{
                            leaf priority{
                                type uint32;
                            }
                        }
                    }
                    container lacp{
                        leaf fast-switchover{
                            description "Used to diable the wait-while timer in LACP state machine";
                            type empty;
                        }
                        leaf rate{
                            type lacp-rate;
                        }
                    }
                }
                case non-bundled{
                    uses vlan-grouping;
                }
            }
            leaf receive-q-length {
                description "No of receive queues for the port. default is 2";
                type uint32;
            }
      
            container descriptors {
                leaf rx-size {
                    description "Size of rx descriptor ring. default is 256";
                    type uint32;
                }
                leaf tx-size {
                    description "Size of tx descriptor ring. default is 256";
                    type uint32;
                }
            }
            leaf numa-socket{
                type int32;
                description "CPU numa socket where the port is attached";
            }
            // Flow control configuration for the port
            uses flow-control;

            container trafgen {
                rwcli:new-mode "trafgen";
                rwpb:msg-new ConfigTrafgen;
                rwpb:msg-flat "true";

                container transmit-params {
                    rwcli:new-mode "transmit-param";
                    description
                        "This is a template for specifying the attributes for packet 
                generation such as transmit rate, packet count, burst size ...";
          
                    uses transmit-param-attr;
                }

                container receive-param  {
                    rwcli:new-mode "receive-param";
                    description
                        "This is a template for specifying the attributes for 
                packet generation such as transmit rate, packet count, 
                burst size ...";
          
                    container receive-echo {
                        leaf on {
                            type empty;
                        }
                    }
                    leaf receive-process-script {
                        type string;
                        rwpb:field-string-max 64;
                    }
                }

                choice template-type {
                    case range-template {
                        container range-template {
                            rwcli:new-mode "range-template";
                            description
                                "This is a template for specifying the contents of packets 
                generated by trafgen application. This template allows the 
                specfiying the ranges for destination mac address, source ip 
                address, destination ip address, source port, destination 
                port and packet sizes. For each of these ranges minimum and 
                maximum values can be specified. The increment value 
                specifies how the values are picked between minimum and 
                maximum values. It is also possible to specify and ip version 
                and L3 protocol type using this template.";
                            uses range-param-attr;
                        }
                    }
                    case sequence-template {
                        container sequence-template {
                            rwcli:new-mode "sequence_template";
                            description
                                "This is a template for specifying the contents of packets 
                generated by trafgen application. This template allows 
                specification of ip version, l3 protocol, destination mac, 
                source ip, destination ip, source port, destination port 
                and packet size. Note that this template is a list and can 
                contain one or more streams of such packets. If the list size 
                is one, all the generated packets will have the same 
                attributes.";
              
                            list  sequence {
                                key "id";
                                rwcli:new-mode "sequence-id";
                                rwpb:field-inline-max yang;
                                max-elements 32;
                                leaf id {
                                    description "Sequence Id";
                                    type uint32;
                                }              
                                uses template-attr;
                            }
                        }
                    }
                    case single-template {
                        container single-template {
                            rwcli:new-mode "single-template";
              
                            description
                                "This template allows specifying the contents of packets 
                generated by trafgen application. This template supports 
                specfiying the destination mac address, source ip address, 
                destination ip address, source port, destination port and 
                packet sizes. It is also possible to specify and ip version
                and L3 protocol type using this template.";

                            uses template-attr;
                        }
                    }

                }
            }
        }
    }


    /*
      +--rw network-context
      +-- rw lb-profile* [name]
      |   +-- rw name
      |   +-- rw destination-nat* [real-ip]
      |       +-- rw real-ip
      |       +-- rw tcp-port
      |       +-- rw udp-port
      |       +-- rw source-ip
      +-- rw load-balancer*[name]
      +-- rw name
      +-- virtual-ip
      +-- tcp-port
      +-- udp-port
      +-- lb-profile
    */
    augment /rwbase:colony/rwbase:network-context {
        uses ipdomain;
        list vrf {
            rwpb:msg-new ConfigVrf;
            key "name";
            max-elements 32;
            leaf name {
                description "Name of VRF";
                rwpb:field-string-max 64;
                rwpb:field-inline "true";
                type string;
            }

            uses ipdomain;
        }
  
        list  lb-profile {
            rwpb:msg-new ConfigLbProfile;
            rwcli:new-mode "lb-profile";
            rwpb:msg-flat true;
            rwpb:field-inline "true";
            rwpb:field-inline-max yang;

            key "name";
            max-elements 32;
      
            leaf name {
                description "Name of lb-profile";
                rwpb:field-string-max 256;
                type string;
            }

            leaf descr-string {
                description "description comment for lb-profile";
                rwpb:field-string-max 32;
                type string;
            }

            list destination-nat {
                key "real-ip";
                rwpb:field-inline-max yang;
                max-elements 32;
        
                leaf real-ip {
                    type rwt:ip-address;
                    rwpb:field-string-max 46;
                }
                leaf tcp-port {
                    type uint16;
                }
                leaf udp-port {
                    type uint16;
                }
                leaf source-ip {
                    type rwt:ip-address;
                    rwpb:field-string-max 46;
                }
            }
        }

        list load-balancer {
            rwpb:msg-new ConfigLoadBalancer;
            rwcli:new-mode "load-balancer";
            rwpb:field-inline "true";
            rwpb:msg-flat true;
            rwpb:field-inline-max yang;

            key "name";
            max-elements 32;
      
            leaf name {
                description "Name of load-balancer";
                rwpb:field-string-max 256;
                type string;
            }

            leaf descr-string {
                description "description comment for load balancer";
                rwpb:field-string-max 32;
                type string;
            }


            leaf virtual-ip {
                type rwt:ip-address;
                rwpb:field-string-max 46;
            }
            leaf tcp-port {
                type uint16;
            }
            leaf udp-port {
                type uint16;
            }
            leaf lb-profile {
                rwpb:field-string-max 256;
                type string;
            }
        }

        list ip-receiver-application {
            rwpb:msg-new ConfigReceiverApp;
            rwcli:new-mode "ip-receiver-app";
            rwpb:field-inline "true";
            rwpb:msg-flat true;
            rwpb:field-inline-max yang;

            key "name";
            max-elements 32;

            leaf name {
                description "Name of IP Receiver App";
                rwpb:field-string-max 256;
                type string;
            }

            leaf descr-string {
                description "description comment for receiver app";
                rwpb:field-string-max 32;
                type string;
            }

            leaf ip-address {
                description "Address of the receiver application";
                type rwt:ip-address;
                rwpb:field-string-max 46;
            }
            leaf protocol {
                description "Layer 4 protocol for IP";
                type enumeration {
                    enum udp { value 0; }
                    enum tcp  { value 1; }
                }
            }
            leaf port {
                description "L4 port number of the receiver application";
                type uint16;
            }
            leaf data-port {
                description "data UDP port number for the test application";
                type uint16;
            }
            leaf flow-op-batch-size {
              description "flow add/delete operations batch size";
              type uint32;
            }
            leaf flow-op-interval-milliseconds {
              description "flow add/delete operations batch intervals";
              type uint32;
            }
            leaf flow-op-initial-count {
              description "initial number of flows to add before starting add/del operations";
              type uint64;
            }
            leaf action {
                description "Action to be performed on received packet";
                type enumeration {
                    enum drop { value 0; }
                    enum echo { value 1; }
                    enum pktgen { value 2; }
                    enum flowop { value 3; }
                }
            }
        }

        list scriptable-lb {
            rwpb:msg-new ScriptableLBCfg;
            rwpb:msg-flat true;
            rwpb:field-inline "true";
            rwpb:field-inline-max yang;
            rwcli:new-mode "scriptable-lb";
          
            max-elements 1;
          
            key "name";
        
            leaf name {
                description "Scriptable LB Name";
                type string;
                rwpb:field-string-max 64;
            }

            container plugin-script {
                uses script;
            }

            container resource-requirement {
              container fastpath {
                leaf cpu-core {
                  type uint32;
                }
              }
            }

            leaf vm-preference {
              type enumeration {
                enum any {value 0; }
                enum avoid-lead {value 1; }
                enum avoid-external-lead {value 2; }
              }
            }

            container receive-function {
                rwcli:new-mode "receive-function";
                uses receive-function-info;
            }
            container classify-function {
                rwcli:new-mode "classify-function";
                uses classify-function-info;
            }
            container server-selection-function {
                rwcli:new-mode "selection-function";
                uses server-selection-function-info;
            }
            container transform-function {
                rwcli:new-mode "transform-function";
                uses transform-function-info;
            }
        }

    }
    
    
    /* ATTN: check rw-base to see if more definitions should be added.

       +-- rw node*[id]
       +-- rw id
       +-- rw trafgen-template
       |   +-- rw (template-type)
       |       +-- : rw (range-template)
       |       |    +-- rw port* [id]
       |       |       +-- rw id
       |       |       +-- rw GROUPING range-param-attr
       |       +-- : rw (sequence-template)
       |       |   +-- rw port* [id]
       |       |       +-- rw id
       |       |       +-- rw sequence* [id]
       |       |           +-- rw id
       |       |           +-- rw GROUPING template-attr
       |       +-- : rw (single-template)
       |       |   +-- rw port* [id]
       |       |       +-- rw id
       |       |       +-- rw GROUPING template-attr
       |       +-- : rw (transmit-params)
       |       |   +-- rw port* [id]
       |       |       +-- rw id
       |       |       +-- rw GROUPING transmit-params
       |       +-- : rw (rx-params)
       |           +-- rw port* [id]
       |           +-- rw id
       |           +-- (...)
       +-- rw port* [name]
       +-- rw name
       +-- rw open
       |   +-- rw ip-fastpat
       |   +-- rw trafgen
       +-- rw receive-q-length
       +-- rw descriptors (...)
       +-- rw flow-control (...)
       +-- rw bind (...)             
    */
    
    /**
     * RPCs for fast path
     */
    rpc start {
        input {      
            container colony {
                rwpb:msg-new StartTraffic;
                rwpb:msg-flat true;
                rwpb:field-inline "true";
                leaf name {
                    rwpb:field-inline "true";
                    rwpb:field-string-max 64;
                    type string;
                }
                container traffic {
                    choice port-range {
                        case  all {
                            leaf all {
                                type empty;
                            }
                        }
                        case  port {
                            leaf port-name {
                                rwpb:field-inline "true";
                                rwpb:field-string-max 64;
                                type string;
                            }
                        }
                    }
                }
                container ip-receiver-app {
                    leaf name {
                        rwpb:field-inline "true";
                        rwpb:field-string-max 64;
                        type string;
                    }
                }
            }
        }
    }
  
    rpc stop {
        input {
            container colony {
                rwpb:msg-new StopTraffic;
                rwpb:msg-flat true;
                rwpb:field-inline "true";
                leaf name {
                    rwpb:field-inline "true";
                    rwpb:field-string-max 64;
                    type string;
                }
                container traffic {
                    choice port-range {
                        case  all {
                            leaf all {
                                type empty;
                            }
                        }
                        case  port {
                            leaf port-name {
                                rwpb:field-inline "true";
                                rwpb:field-string-max 64;
                                type string;
                            }
                        }
                    }
                }
                container ip-receiver-app {
                    leaf name {
                        rwpb:field-inline "true";
                        rwpb:field-string-max 64;
                        type string;
                    }
                }                                  
            }
        }
        output {
         list flowops-stats {
          key "fastpath-instance";
          leaf fastpath-instance { type uint32; }
          leaf flow-ops-attempts { type uint64; }
          leaf flow-add-failures { type uint64; }
          leaf flow-del-failures { type uint64; }
          leaf flow-ops-rate     { type uint64; }
        }
      }
    }

    rpc fpath-clear {
        input {
            container colony {
                rwpb:msg-new ClearPort;
                rwpb:msg-flat true;
                rwpb:field-inline "true";
                leaf name {
                    rwpb:field-inline "true";
                    rwpb:field-string-max 64;
                    type string;
                }
                container counters {
                    choice port-range {
                        case  all {
                            leaf all {
                                type empty;
                            }
                        }
                        case  port {
                            leaf port-name {
                                rwpb:field-inline "true";
                                rwpb:field-string-max 64;
                                type string;
                            }
                        }
                    }
                }
                container trafgen-counters {
                    choice port-range {
                        case  all {
                            leaf all {
                                type empty;
                            }
                        }
                        case  port {
                            leaf port-name {
                                rwpb:field-inline "true";
                                rwpb:field-string-max 64;
                                type string;
                            }
                        }
                    }
                }
                container logical-port-counters{
                    choice lport-range{
                        case all {
                            leaf all {
                                type empty;
                            }
                        }
                        case lport{
                            leaf lport-id{
                                type uint32;
                            }
                        }
                    }
                }
                container kernel-stat-counters{
                    choice instance{
                        case all {
                            leaf all{
                                type empty;
                            }
                        }
                        case fastpath-instance {
                            leaf fastpath-instance{
                                type uint32;
                            }
                        }
                    }
                }
                container lacp-counters{
                    choice port-range{
                        case  all {
                            leaf all {
                                type empty;
                            }
                        }
                        case  port {
                            leaf port-name {
                                rwpb:field-inline "true";
                                rwpb:field-string-max 64;
                                type string;
                            }
                        }
                    }
                }
                container ip-classifier-counters{
                    choice instance{
                        case all {
                            leaf all{
                                type empty;
                            }
                        }
                        case fastpath-instance {
                            leaf fastpath-instance{
                                type uint32;
                            }
                        }
                    }
                }
                container external-app-counters {
                    choice instance{
                        case all {
                            leaf all{
                                type empty;
                            }
                        }
                        case fastpath-instance {
                            leaf fastpath-instance{
                                type uint32;
                            }
                        }
                    }
                }
                container scriptable-loadbalancer-counters { 
                    choice instance{
                        case all {
                            leaf all{
                                type empty;
                            }
                        }
                        case fastpath-instance {
                            leaf fastpath-instance{
                                type uint32;
                            }
                        }
                    }
                }
            }      
        }
    }
            
    rpc fpath-debug {
        input {
            container node {      
                rwpb:msg-new FpathDebug;
                rwpb:msg-flat "true";
                rwpb:field-inline "true";

                leaf id {
                    type uint32;
                }

                choice operation {
                    container show {
                        description "Show operation";
                        container thread {
                            presence true;
                            description "Information on thread";
                            leaf lcore {
                                type uint32;
                                description "Core Id";
                            }
                        } //thread
                        leaf work {
                            type empty;
                            description "Information on work";
                        } //thread
                        leaf lcore {
                            type empty;
                            description "Information on lcore";
                        } //lcore
                        container table {
                            presence true;
                            description "Information on FastPath related global tables";
                            leaf vsapid-vfapid-bindings {
                                description "VSAPID to VFAPID bindings";
                                type empty;
                            }
                            leaf vfapid-address-bindings {
                                description "VFAPID to Address bindings";
                                type empty;
                            }
                            container fpath-hashbin-bindings {
                                presence true;
                                description "Fpath instance to hashbins bindings";
                                leaf rwfpath-instance {
                                    type int32;
                                    description "Fpath instance id";
                                }
                            }
                            leaf ip-signature-bindings {
                                type empty;
                                description "IP Signature Table";
                            }
                            leaf registered-fpath {
                                type empty;
                                description "Registered Fpath";
                            }
                            leaf classifier-service {
                                type empty;
                                description "Classifier services";
                            }
                        } // table
                    } //show   
                    container start {
                        description "Start operation";
                        container thread {
                            leaf lcore {
                                type uint32;
                                description "Core Id";
                            }
                        } //thread
                        leaf fast-path {
                            type empty;
                            description "fast path";
                        } //fast-path
                        leaf hashbin-distribution {
                            type empty;
                            description "Initiate Hashbin distribution";
                        } // hashbin-distribution
                        leaf fast-flow {
                          type empty;
                          description "Start Fast-Flow service";
                        }
                        
                    } //start
                    container stop {
                        container thread {
                            description "Stop operation";
                            leaf lcore {
                                type uint32;
                                description "Core Id";
                            }
                        } //thread
                        leaf fast-path {
                            type empty;
                            description "fast path";
                        } //fast-path
                        leaf fast-flow {
                          type empty;
                          description "Stop Fast-Flow service";
                        }
                    } //stop
                    container assign {
                        description "Assign operation";             
                        leaf work-id {
                            type uint32;
                            description "Work Id";
                        }
                        leaf lcore-id {
                            type uint32;
                            description "lcore-id";
                        }          
                    } //assign
                    container test{
                        description "Test operation";
                        container rwfpath {
                            description "Test operation for RW.Fpath";
                            container msg-test{
                                description "Messenging test";
                                leaf fpctrl-instance {
                                    description "RW.Fpath instance";
                                    type uint32;
                                }
                            }
                        }
                        container rwfpctrl {
                            description "Test operation for RW.Fpath";
                            container msg-test{
                                description "Messenging test";
                                leaf fpath-instance {
                                    description "RW.Fpath instance";
                                    type uint32;
                                }
                            }
                        }
                    } // test
                } // choice
            } // node
        } // RPC fath-debug
    
        output {
            rwpb:msg-proto-max-size "1700000";
            rwpb:msg-new FpathDebugOut;
            container work-info {
                rwpb:msg-new RwWorkInfo;
                rwpb:msg-flat true;
                rwpb:msg-proto-max-size "1700000";
        
                list work {
                    rwpb:field-inline-max yang;
                    max-elements 256;
          
                    key "id";
          
                    leaf id {
                        type uint32;
                        description "Id";
                    }
          
                    leaf name {
                        type string;
                        rwpb:field-string-max 64;
                        description "Work name";
                    }
                    leaf port-id {
                        type rwt:port-number;
                        description "Port Id";
                    }
                    leaf port-name {
                        type rwfpath-base-string;
                        rwpb:field-string-max 256;
                        description "Port Name";
                    }
          
                    leaf work-instance-id {
                        type int32;
                        description "Work instance Id";
                    }
                    leaf lcore-id {
                        type int32;
                        description "lcore assigned";
                    }
                    leaf resched-attempts {
                        type int32;
                        description "number of times works rescheduled to different lcores";
                    }
                }
            }

            container lcore-info {
                rwpb:msg-new RwLcoreInfo;
                rwpb:msg-flat true;
        
        
                list lcore {
                    rwpb:field-inline-max yang;
                    max-elements 64;//RTE_MAX_LCORE
          
                    key "id";
          
                    leaf id {
                        type uint32;
                        description "Id";
                    }
          
                    leaf socket {
                        type int32;
                        description "NUMA Socket Id";
                    }
          
                    leaf core-id {
                        type uint32;
                        description "Core Id";
                    }
          
                    leaf thread-status {
                        type string;
                        rwpb:field-string-max 256;
                        description "Thread Status";
                    }
          
                    leaf thread-type {
                        type string;
                        rwpb:field-string-max 256;
                        description "Thread Type";
                    }
          
                    leaf tx-q-id {
                        type uint32;
                        description "Tx Q Id";
                    }
                    leaf num-works {
                        type uint32;
                        description "Num works Assigned"; 
                    }
                }
            }
      
            container lcore-id-info {
                rwpb:msg-new RwLcoreIdInfo;
                rwpb:msg-flat true;
        
        
                leaf id {
                    type uint32;
                    description "Id";
                }
                list work {
                    rwpb:field-inline-max yang;
                    max-elements 32;
          
                    key "work-id";
          
                    leaf work-id {
                        type uint32;
                        description "Work Id";
                    }
          
                    leaf work-name {
                        type string;
                        rwpb:field-string-max 64;
                        description "Work name";
                    }
                }
            }
            container lcore_thread-info {
                rwpb:msg-new RwFpDebugLcoreThreadInfo;
                rwpb:msg-flat true;
        
        
                leaf lcore-id {
                    type int32;
                    description "lcore Id";
                }
        
                leaf thread-type {
                    type string;
                    rwpb:field-string-max 256;
                    description "Thread Type";
                }
        
                leaf tx-q-id {
                    type uint32;
                    description "Tx Q Id";
                }
        
                list work_queue {
                    rwpb:field-inline-max yang;
                    max-elements 128; // TBD
          
                    key "work_id";
          
                    leaf work_id {
                        type uint32;
                        description "Work instance Id";
                    }
                    leaf work_name {
                        type string;
                        rwpb:field-string-max 64;
                        description "Work name";
                    }
                    leaf work_flag {
                        type uint16;
                        description "bitmap flag for work property";
                    }
                    leaf work_metric {
                        type uint64;
                        description "work accomplished so far";
                    }
                    leaf work_metric_checkpoint {
                        type uint64;
                        description "work accomplished last snapshot";
                    }
                    leaf work_cont_low {
                        type uint16;
                        description "Number conscecute low work cycles";
                    }
                } //Work Info

                list app-data {
                    rwpb:field-inline-max yang;
                    max-elements 4;

                    key "app_id";

                    leaf app_id {
                        type uint32;
                        description "Channel Application Id";
                    }
        
                    list channel-stats {
                        rwpb:field-inline-max yang;
                        max-elements 32;

                        key "channel_id";

                        leaf channel_id {
                            type uint32;
                            description "Channel Id";
                        }
        
                        leaf total-transmit {
                            type uint64;
                            description "Total transmitted packets";
                        }

                        leaf total-dropped {
                            type uint64;
                            description "Total dropped packets";
                        }
                    }
                }
            } // thread-info
            container vsapid-table {
                rwpb:msg-new RwFpVsapidTable;
                rwpb:msg-flat true;
        

                list vsapid-to-vfapid {
                    rwpb:field-inline-max yang;
                    max-elements 1024; 

                    key "vsapid";
                    leaf vsapid {
                        type int32;
                        description "Virtual Service Access Point ID";
                    }
                    leaf fpath {
                        type int32;
                        description "Fpath Instance";
                    }
                    leaf groupid {
                        type int32;
                        description "Resource Group ID";
                    }
                    leaf vfapid {
                        description "Virtual Fabric Access Port ID";
                        type int32;
                    }  
                } // vsapid-to-vfapid list
            }
            container vfapid-table {
                rwpb:msg-new RwFpVfapidTable;
                rwpb:msg-flat true;
        
                list vfapid-to-addr {
                    rwpb:field-inline-max yang;
                    max-elements 1024; 

                    key "vfapid";

                    leaf vfapid {
                        type int32;
                        description "Virtual Fabric Access Port ID";
                    }
                    leaf groupid {
                        type uint32;
                        description "Group id";
                    }
                    leaf fpath {
                        type int32;
                        description "Fpath Instance";
                    }
                    leaf ncid {
                        type int32;
                        description "Network Context ID";
                    }
                    leaf ip_address {
                        type rwt:ip-address;
                        rwpb:field-string-max 46;
                        description "IP Address where VFAPID is accessible";
                    }
                    leaf port {
                        type int32;
                        description "UDP port where VFAPID is accessible";
                    }
                }
            } // vfapid-table
            container hashbin-table {
                rwpb:msg-new RwFpHashbinTable;
                rwpb:msg-flat true;
        

                leaf fpath_hashbin_credits {
                    type uint32;
                    description "RW.Fpath hashbin credits";
                }

                leaf total_hashbin_credits {
                    type uint32;
                    description "Cumulative hashbin credits";
                }

                leaf total_hashbins_assigned {
                    type uint32;
                    description "Total hashbins assigned to this RW.Fpath Instance";
                }
        
                list hashbins {
                    rwpb:field-inline-max yang;            
                    max-elements 1024; 
                    container hashbin-range {
                        leaf hashbin-start{
                            type int32;
                            description "Hashbin Range Start";
                        }
                        leaf hashbin-end {
                            type int32;
                            description "Hashbin Range End";
                        }            
                    }
                } // hashbins
            } // hashbin-table
            container ip-signature-table {
                rwpb:msg-new RwFpIpsigTable;
                rwpb:msg-flat true;
                rwpb:msg-proto-max-size "1300000";
        
                list ip-signature {
                    rwpb:field-inline-max yang;
                    max-elements 1024; 

                    key "sig-id";

                    leaf sig-id {
                        description "Signature ID";
                        type uint32;
                    }
                    leaf flow-type {
                        description "Flow Type";
                        type uint32;
                    }
                    leaf ncid {
                        description "Network Context ID";
                        type uint32;
                    }
                    leaf ip-address {
                        description "IP Address";
                        type rwt:ip-address;
                        rwpb:field-string-max 46;
                    }
          
                    leaf sig-mask {
                        description "Signature Mask";
                        type string;
                        rwpb:field-string-max 512;
                    }
                    leaf sig-key {
                        description "Signature Key";
                        type string;
                        rwpb:field-string-max 512;
                    }
                }
            } // IP Signature Table
            container registered-fpath {
                rwpb:msg-new RwFpFpath;
                rwpb:msg-flat true;
        
                leaf Fpctrl-id {
                    type uint32;
                    description "Fpctrl instance";
                }
        
                list fpath {
                    rwpb:field-inline-max yang;
                    max-elements 1024; 
                    key "fpath-id";
                    leaf fpath-id {
                        type uint32;
                        description "Fpath ID";
                    }
                }
            } // registered-fpath

            container classifier-service {
                rwpb:msg-new SvcTable;
                rwpb:msg-flat true;
                rwpb:msg-proto-max-size "230448";
        
                leaf Fpctrl-id {
                    type uint32;
                    description "Fpctrl instance";
                }
        
                list service_list{
                    rwpb:field-inline-max yang;
                    rwpb:field-inline "true";
                    max-elements 256; 
                    key "service-id";
          
                    leaf service-id {
                        type uint32;
                        description "Service Id";
                    }
                    leaf user-application {
                        type string;
                        rwpb:field-string-max 256;
                        description "User Application using the classifier service";
                    }
                    leaf ipfp-plugin-id {
                        type uint32;
                        description "IPFP plugin ID of user application";
                    }
                    list signature_list {
                      rwpb:field-inline-max yang;
                      rwpb:field-inline "true";
                      max-elements 16; 
                      key "signature-id";
                      leaf signature-id {
                        type uint32;
                        description "Signature ID for receiver signature used by Classifier";
                      }
                    }
                    
                    leaf key-extraction-method {
                      type enumeration {
                        enum plugin { value 0; }
                        enum script { value 1; }
                      }
                      description "Key extraction mechanism";
                    }
                }
            } // Classifier service
        } // output
    } // fpath_debug
  
    container return_status {
        rwpb:msg-new ReturnStatus;
        rwpb:field-inline "true";
        rwpb:msg-flat "true";
        config "false";
    
        leaf error_number {
            type int32;
            description "Error number";
        }
        leaf error_string {
            type string;
            rwpb:field-string-max 128;
            description "Error string value";
        }
    }     

  augment /rwbase:colony {
    list packet-filters {
      rwpb:field-inline "true";
        max-elements 1;
      rwpb:msg-flat "true";
      rwpb:msg-proto-max-size "263064";
      key "network-context";
      config "false";
      leaf network-context {
        description "Context name";
        type string;
        rwpb:field-string-max 46;
      }
      list filter {
        rwpb:field-inline "true";
        max-elements 16;
        key "type inode-id lport-id";
        leaf inode-id{
          type uint32;
        }
        leaf type {
          type filter-type;
        }
        leaf lport-id{
          type uint32;
        }
        list bpf-instruction{
          rwpb:field-inline "true";
          max-elements 256;
          leaf code{
            type uint32;
          }
          leaf jt{
            type uint32;
          }
          leaf jf{
            type uint32;
          }
          leaf k{
            type uint32;
          }
        }
      }
    }
  }

} // module rw-fpath
