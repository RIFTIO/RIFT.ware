/*
 * STANDARD_RIFT_IO_COPYRIGHT
 *
 */

module exampletest
{
  namespace "http://riftio.com/ns/core/util/yangtools/tests/exampletest";
  prefix "gitest";

  import rw-pb-ext { prefix "rwpb"; }
  description "This YANG module models a Company";

  revision 2014-05-27 {
    description "Initial version"; }

  rwpb:file-pbc-include "rwtypes.h";
  rwpb:file-pbc-include "rw_ip.h";
  rwpb:file-pbc-include "rw_sklist.h";

  container flat {
    rwpb:msg-new RwFlat;
    rwpb:msg-flat "true";
    container inner-a {
      leaf a {
        rwpb:field-string-max 32;
        type string;
      }
    }

    container inner-b {
      leaf b {
        rwpb:field-string-max 32;
        type string;
      }
    }
  }
}
