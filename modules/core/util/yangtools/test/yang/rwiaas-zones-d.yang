/*
 * STANDARD_RIFT_IO_COPYRIGHT
 *
 */

module rwiaas-zones-d {
  namespace "http://riftio.com/ns/riftware-1.0/rwiaas-zones";
  prefix "rwzones";
  
  import rw-pb-ext { prefix "rwpb"; }
  import rw-yang-types { prefix rwt; }
  import ietf-inet-types { prefix "inet"; }
  import ietf-yang-types { prefix "yang"; }

  revision 2015-01-28 {
    description
      "Initial revision. This YANG file captures the
      data model for provisioning IaaS layer zones.";     
    reference
      "Derived from earlier versions of base YANG files"; 
  }

  list availability-zones {
    description
      "List of availability zones.";
    key name;
    leaf name {
      description "Name of the avialability zone.";
      type string;
    }   
  } 
}
