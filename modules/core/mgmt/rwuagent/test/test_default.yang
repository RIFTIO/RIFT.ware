/* STANDARD_RIFT_IO_COPYRIGHT */

/**
 * @file test_default.yang
 * @author Balaji Rajappa 
 * @date 2016/04/28
 * @brief YANG definition for unit testing DomMerger 
 */

module test_default
{
  namespace "http://riftio.com/ns/core/mgmt/uagent/test/test_default";
  prefix "td";

  description
    "Yang definition used for testing fill-defaults of DomMerger";
  
  revision 2016-04-28 {
    description "Initial version"; }

  container deep {
    container has-default {
      leaf def {
        type string;
        default "is-default";
      }
      leaf non-def {
        type string;
      }
      container also-has-default {
        leaf also-def {
          type string;
          default "also-default";
        }
      }
    }
  }
}
