/*
 * STANDARD_RIFT_IO_COPYRIGHT
 *
 */

module interfaces {

  namespace "http://riftio.com/ns/core/mgmt/rwuagent/test/interfaces";
  prefix interfaces;

  import ietf-yang-types { prefix yang; }
  import ietf-inet-types { prefix inet; }
  import ut-types { prefix tps; }
  import rw-c-types { prefix rwct; }
  import rw-pb-ext { prefix rwpb; }

  description " System Interfaces configuration ";

  revision "2015-10-31" {
    description "Initial revision";
  }

  typedef interfaceSpeed {
    type enumeration {
      enum ten { value "10";}
      enum hundred { value "100";}
      enum thousand { value "1000"; }
    }
  }

  typedef interfaceDuplex {
    type enumeration {
      enum "half";
      enum "full";
    }
  }

  grouping commonPacketsCounters {
    leaf bytes {
      type yang:counter64;
    }
    leaf packets {
      type yang:counter64;
    }
    leaf errors {
      type yang:counter32;
    }
    leaf dropped {
      type yang:counter32;
    }
  }

  grouping txPacketsCounters {
    uses commonPacketsCounters;
    leaf collisions {
      type yang:counter32;
    }
  }

  container interfaces {
    list interface {
      rwpb:msg-new "Interface";
      must "(duplex and speed) or (not(duplex) and not(speed))" {
        error-message "Neither or both of 'speed' and 'duplex'
            must be set";
      }
      key name;
      leaf name {
        type tps:interfaceName;
      }
      leaf description {
        type string;
      }
      leaf enabled {
        type boolean;
        default true;
      }
      leaf speed {
        type interfaceSpeed;
        description "not supported for all types of interfaces";
      }
      leaf duplex {
        type interfaceDuplex;
        description "not supported for all types of interfaces";
      }
      leaf mtu {
        type int16 {
          range "68..1500";
        }
      }
      leaf mac {
        type rwct:rw-mac-addr;
      }
      container status {
        config false;

        leaf link {
          type enumeration {
            enum up;
            enum down;
          }
        }
        leaf speed {
          type interfaceSpeed;
        }
        leaf duplex {
          type interfaceDuplex;
        }
        leaf mtu {
          type int32;
        }
        leaf mac {
          type rwct:rw-mac-addr;
        }
        container receive {
          uses commonPacketsCounters;
        }
        container transmit {
          uses txPacketsCounters;
        }
      }
      list unit {
        key name;
        leaf name {
          type tps:interfaceLogicalUnit;
        }
        leaf enabled {
          type boolean;
        }
        leaf description {
          type string;
        }
        leaf vlan-id {
          type uint16 {
            range "1..4094";
          }
        }
        container status {
          container receive {
            uses commonPacketsCounters;
          }
          container transmit {
            uses txPacketsCounters;
          }
        }
        container family {
          choice family {
            case c1 {
              container inet {
                list address {
                  key name;
                  leaf name {
                    type inet:ipv4-address;
                  }
                  leaf prefix-length {
                    type tps:prefixLengthIPv4;
                  }
                  leaf broadcast {
                    type inet:ipv4-address;
                  }
                }
              }
            }
            case c2 {
              container inet6 {
                list address {
                  key name;
                  leaf name {
                    type inet:ipv6-address;
                  }
                  leaf prefix-length {
                    type tps:prefixLengthIPv6;
                  }
                }
              }
            }
          }
        }
      }
    }
  }

  rpc clear-interface {
    input {
      rwpb:msg-new "ClearInterface";
      container interface {
        leaf name {
           type tps:interfaceName;
        }
        leaf receive {
          type empty;
        }
        leaf transmit {
          type empty;
        }
      }
    }

    output {
      rwpb:msg-new "ClearInterfaceOp";
      leaf status {
        type string;
      }
    }
  }
}
