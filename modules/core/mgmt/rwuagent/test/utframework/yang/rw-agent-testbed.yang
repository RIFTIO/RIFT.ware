/* STANDARD_RIFT_IO_COPYRIGHT */

/**
 * @file rw-agent-testbed.yang
 * @date 2016/03/15
 * @brief MgmtAgent tests
 */

module rw-agent-testbed
{
  namespace "http://riftio.com/ns/riftware-1.0/rw-agent-testbed";
  prefix "agt-tb";

  import rw-pb-ext {
    prefix "rwpb";
  }

  revision 2016-03-15 {
    description "Initial revision.";
  }

  rpc agent-tests {

    input {

      choice test {

        container all {
          description "Run all tests";

          leaf continue-on-failure {
            description "Continue execution on failure";
            type boolean;
            default false; 
          }
        }

        container netconf-tests { 

          choice test {

            container all {
              description "Run all netconf-tests";
            }

            container edit-config {
              description "Test Edit config via NETCONF";
            }

            container notif {
              description "Test notification via NETCONF";
            }

            container large-binary-blob {
              description "Test large binary data";
            }
          }
        }

        container pb-request-tests {

          choice test {

            container ec-merge {
              description "Test PB-REQUEST edit-conf merge";
            }

            container ec-delete {
              description "Test PB-REQUEST edit-conf delete";
            }

            container all {
              description "Run all pb-request-tests";
            }
          }
        }
      }
    }

    output {

      rwpb:msg-new "AgentTestsOp";

      leaf total_tests {
        description "Total tests in the testbed";
        type uint64;
      }

      leaf passed_count {
        description "Number of failed tests";
        type uint64;
      }

      leaf failed_count {
        description "Number of failed tests";
        type uint64;
      }

      leaf-list failed_tests {
        description "List of failed tests";
        type string;
      }
    }
  }
}
