/* STANDARD_RIFT_IO_COPYRIGHT */

/**
 * @file vehicle-augment-b.yang
 * @author Max Beckett
 * @date 7/23/2015
 * @brief YANG definition for unit testing rwrestconf 
 */

module vehicle-augment-b
{
  // exception to naming rule because it's a "real world" analog
  namespace "http://riftio.com/ns/core/mgmt/rwrestconf/test/vehicle-augment-b";
  prefix "vehicle-augment-b";
  
  import vehicle-b {
    prefix vehiclea;
  }

  container clash {
    leaf bar {
      type string;
    }
  }

  augment /vehiclea:car {

    list extras {

      key "name-e";

      leaf name-e {
        type string;
      }

      container engine {

        leaf horsepower {
          type string;
        }

        leaf cylinders {
          type uint8;
        }
      }

      leaf speakers {
        type uint8;
      }

      leaf seats {
        type string;
      }
        
      list features {
        key "package";
        leaf package {
          type string;
        }

        list items{
          key "name";
          leaf name {
            type string;
          }
          leaf price {
            type uint32;
          }
        }
      }
    }
  }
}
