/*
 * STANDARD_RIFT_IO_COPYRIGHT
 *
 */

module rw-agent-testbed-tailf {

  namespace "http://riftio.com/ns/core/mgmt/rwuagent/test/rw-agent-testbed-tailf";
  prefix "tb-tailf";

  import rw-agent-testbed {
    prefix "rw-agent-testbed";
  }

  import tailf-common {
    prefix "tailf";
  }

  tailf:annotate "/rw-agent-testbed:agent-tests" {
    tailf:actionpoint rw_actionpoint;
  }
}
