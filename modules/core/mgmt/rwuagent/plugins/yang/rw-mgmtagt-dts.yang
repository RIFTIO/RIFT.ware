/* STANDARD_RIFT_IO_COPYRIGHT */

module rw-mgmtagt-dts
{
  namespace "http://riftio.com/ns/riftware-1.0/rw-mgmtagt-dts";
  prefix "rw-mgmtagt-dts";

  import rw-pb-ext {
    prefix "rwpb";
  }

  revision 2016-04-10 {
    description "Initial revision";
  }

  typedef pb-request-type {
    type enumeration {
      enum edit-config { value 1; }
      enum rpc { value 2; }
      enum get { value 3; }
      enum get-config { value 4; }
    }
  }

  typedef pb-edit-type {
    type enumeration {
      enum merge { value 1; }
      enum create { value 2; }
      enum replace { value 3; }
      enum delete { value 4; }
    }
  }

  rpc mgmt-agent-dts {
    input {
      choice action {
        case pb-request {
          container pb-request {
            rwpb:msg-new PbRequest;
            presence true; // ATTN: Hack workaround for RIFT-9591

            choice key {
              mandatory true;
              leaf keyspec {
                type binary;
              }
              leaf xpath {
                type string;
              }
            }

            choice payload {
              leaf data {
                type binary;
              }
              leaf blobxml {
                type string;
              }
            }

            leaf request-type {
              mandatory true;
              type rw-mgmtagt-dts:pb-request-type;
            }

            leaf edit-type {
              type rw-mgmtagt-dts:pb-edit-type;
            }
          }
        }
      }
    }

    output {
      choice action {
        container pb-request {
          rwpb:msg-new PbIntRsp;
          leaf error {
            type string;
          }
          leaf keyspec {
            type binary;
          }
          leaf xpath {
            type string;
          }
          choice payload {
            leaf data {
              type binary;
            }
            leaf blobxml {
              type string;
            }
          }
        }
      }
    }
  }
}
