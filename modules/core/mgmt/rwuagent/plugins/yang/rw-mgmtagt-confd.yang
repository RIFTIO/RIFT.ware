/* STANDARD_RIFT_IO_COPYRIGHT */

/**
 * @file rw-mgmtagt-confd.yang
 * @brief Yang module specific to Confd
 */

module rw-mgmtagt-confd
{
  namespace "http://riftio.com/ns/riftware-1.0/rw-mgmtagt-confd";
  prefix "rw-mgmtagt-confd";

  import rw-pb-ext {
    prefix "rwpb";
  }

  import rw-mgmtagt
  {
    prefix "rw-mgmtagt";
  }

  revision 2016-03-28 {
    description
      "Initial revision.";
    reference
      "Derived from earlier versions of base YANG files";
  }

  typedef callback-type {
    description
      "An enumeration for the types of callbacks invoked by confd to
      the uagent in context of the uagent being a data provider";
    type enumeration
    {
      enum exists-optional;
      enum get-elem;
      enum get-next;
      enum set-elem;
      enum create;
      enum remove;
      enum find-next;
      enum num-instances;
      enum get-object;
      enum get-next-object;
      enum find-next-object;
      enum get-case;
      enum set-case;
      enum get-attrs;
      enum set-attr;
      enum move-after;
      enum write-all;
    }
  }

  augment /rw-mgmtagt:uagent {

   container confd {
      rwpb:msg-new Confd;
      config false;
      description
        "Information regarding interaction with the confd agent";

      leaf total-dom-lifetime {
        type uint64;
        description
          "Total time spent in DOM operations";
      }

      container dom-refresh-period {
        leaf cli-dom-refresh-period {
          type uint32;
          units milliseconds;
          description
            "Time in milliseconds after which cached DOM data will get
            flushed for CLI session.";
        }

        leaf nc-rest-dom-refresh-period {
          type uint32;
          units milliseconds;
          description
            "Time in milliseconds after which cached DOM data will get
            flushed for RESTCONF/NETCONF session.";
        }
      }

      list client {
        rwpb:msg-new Client;
        description
          "Interaction with each client type";

        key identifier;
        leaf identifier {
          description
            "An internal identifier for each client used by confd.  0
            corresponds to clients that have exited";
          type uint64;
        }

        list cached_dom {
          rwpb:msg-new CachedDom;
          key index;

          leaf index {
          type uint16;
          description
            "A false index";
          }

          leaf path {
            type string;
            description
              "The hkey path that created this entry";
          }

          leaf dts-keyspec {
            description
              "Keyspec used for DTS if a query was needed.  Not set for
              requests served from local operational dom";
            type string;
          }


          leaf create-time {
            type uint64;
            description
              "Time in microseconds from when the dom was created to
              its last access";
          }

          leaf usage-time {
            type uint64;
            description
              "Time in microseconds from when the dom was created to
              its last access";
          }

          list callbacks {
            rwpb:msg-new Callbacks;
            key type;

            leaf type {
              description
                "The type of callback invoked";
              type callback-type;
            }

            leaf count {
              description
                "Number of times a callback was invoked";
              type uint16;
            }
          }
        }
      }
    }
  }

  rpc mgmt-agent-confd {
    input {
      choice action {
        container clear-stats {
          rwpb:msg-new ClearStats;
          description "Clear the stats";
          leaf confd {
            type empty;
          }
        }

        container dom-refresh-period {
          rwpb:msg-new DomRefreshPeriod;
          leaf cli-dom-refresh-period {
            type uint32;
            units milliseconds;
            description
              "Time in milliseconds after which cached DOM data will get
              flushed for CLI session.";
          }

          leaf nc-rest-dom-refresh-period {
            type uint32;
            units milliseconds;
            description
              "Time in milliseconds after which cached DOM data will get
              flushed for RESTCONF/NETCONF session.";
          }
        }
      }
    }
  }

}
