/*
 * STANDARD_RIFT_IO_COPYRIGHT
 *
 */

module rwuagent-cli-annotation
{
  namespace "http://riftio.com/ns/riftware-1.0/rw-mgmtagt-annotation";
  prefix "rw-uagent-ann";

  import rw-mgmtagt
  {
    prefix rw-mgmtagt;
  }

  import tailf-common {
    prefix tailf;
  }

  tailf:annotate "/rw-mgmtagt:mgmt-agent" {
    tailf:actionpoint rw_actionpoint;
  }

  tailf:annotate "/rw-mgmtagt:show-system-info" {
    tailf:actionpoint rw_actionpoint;
  }

  tailf:annotate "/rw-mgmtagt:show-agent-logs" {
    tailf:actionpoint rw_actionpoint;
  }

  tailf:annotate "/rw-mgmtagt:uagent/rw-mgmtagt:state" {
    tailf:callpoint rw_callpoint;
  }

}
