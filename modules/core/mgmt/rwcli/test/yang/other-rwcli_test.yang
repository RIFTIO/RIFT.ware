/*
 * STANDARD_RIFT_IO_COPYRIGHT
 *
 */

module other-rwcli_test
{
  namespace "urn:ietf:params:xml:ns:yang:rift:config";
  prefix "rwclitest";

  import rw-pb-ext {
    prefix "rwpb";
  }

  revision 2014-03-31 {
    description
      "Initial revision.";
    reference
      "RIFT Trafgen Application";
  }

  container show {
    container port {
      rwpb:msg-new ShowPortCounters;
      rwpb:msg-flat "true";

      description "Shows port related counters/stats";
      choice port-id-range  {
        case all {
          leaf all {
            description "List all the available ports";
            type empty;
          }
        }
        case port-id {
          leaf port-id {
            description "Show detailed information for the specified port";
            type uint32;
          }
        }
      }
      container counters {
        description "Lists brief port statistics the ports";
        // rwcli:cli-print-hook "rwcli_plugin-python:default_print";
        choice port-id-range  {
          case all {
            leaf all {
              description "Lists brief port statistics for all the ports";
              type empty;
            }
          }
          case port-id {
            leaf port-id {
              description "Lists detailed port statistics for the specified port id";
              type uint32;
            }
          }
        }
      }
      container queues {
        description "Lists brief per queue statistics the ports";
        container counters {
          description "Lists brief port statistics the ports";
          choice port-id-range  {
            case all {
              leaf all {
                description "Lists brief port statistics for all the ports";
                type empty;
              }
            }
            case port-id {
              leaf port-id {
                description "Lists detailed port statistics for the specified port id";
                type uint32;
              }
            }
          }
        }
      }
    }
  }

  // Testing the idref
  list network {
    key "name";
    leaf name { type string; }
    leaf cidr { type string; }
    list servers {
      key "host";
      leaf host { type string; }
      leaf ip { type string; }
    }
  }

} // module other-rwcli_test
