/* STANDARD_RIFT_IO_COPYRIGHT */

/**
 * @file testncx-cli.yang
 * @author Tom Seidenberg
 * @date 2014/03/05
 * @brief Top-level yang for testing libncx.
 */

module testncx-cli
{
  namespace "http://riftio.com/ns/core/util/yangtools/tests/testncx-cli";
  prefix "tn";

  import testncx-base-cli { prefix "tnb"; }
  import rw-pb-ext { prefix "rwpb"; }
  import rw-cli-ext { prefix "rwcli"; }

  description
    "Top-level yang for testing libncx.";

  revision 2014-03-05 {
    description "Initial version"; }

  typedef relative-ufnt {
    type tnb:ufnt {
      range "-10000000..10000000";
    }
    description "A few months, either way";
  }

  typedef enum_eplus {
    type tnb:enum_e;
    description "Renamed enum_e";
  }

  typedef flags {
    type bits {
      bit a { position 0; }
      bit b { position 1; }
      bit c { position 2; }
      bit d { position 3; }
    }
    description "Some bits";
  }

  identity google {
    base tnb:company;
    description "Google";
  }

  grouping group-top {
    leaf n1 {config true; type int8 {range "-12..14";} }
    leaf n2 { type int16 {range "100..200|300|400..500";} config true; }
    leaf n3 { type int32; config false; }
    leaf n4 { type int64; config false; }
    leaf n5 { type uint8; config true; }
    leaf n6 { type uint16; config true; }
    leaf n7 { type uint32; config false; }
    leaf n8 { type uint64; config false; }

    leaf iref1 { type identityref { base "tnb:company"; } }
    leaf bin1 { type binary {length "2..5";}}
    leaf bits1 { type flags; }
    leaf bool1 { type boolean; }
    leaf dec1 { type decimal64 { fraction-digits 10; } }
    leaf e1 { type empty; }
    leaf s1 { type string{length "2..5";} }

    // ATTN: anyxml is not supported by confd!
    //anyxml axml { config true; }

    leaf u1 {
      type union {
        type string {length "2";pattern "[p-r]*";}
        type tn:flags;
        type identityref { base "tnb:company"; }
        type int8 {range "100..110";}
        type tn:relative-ufnt;
        type decimal64 {fraction-digits "14";}
      }
    }
  }

  // Blows up yangdump to XSD
  augment "/tnb:top" {
    leaf some-more { type string; }
  }

  container top {

    rwpb:msg-new TncxTop;

    container a {
      rwcli:new-mode "test-new-mode";
      uses tnb:group-a;
    }

    container a1 {
      uses tnb:group-a {
        augment "cont-in-a" {
          leaf aug1 { type string; description "An augment"; }
        }
      }
    }

    container b {
      uses tnb:group-b;
    }

    container c {
      leaf c {
        type identityref { base "tnb:company"; }
      }
    }

    container d {
      uses group-top {
        refine "n1" { config false; }
        refine "n2" { config false; }
        refine "n3" { config true; }
        refine "n4" { config true; }
        refine "n5" { config false; }
        refine "n6" { config false; }
        refine "n7" { config true; }
        refine "n8" { config true; }
      }
    }

    container e {
      uses group-top;
    }

    container f {
      leaf with-ns { type tn:relative-ufnt; }
      leaf without-ns { type relative-ufnt; }
    }

    container g {
      leaf ge1 { type tnb:enum_e; }
      leaf ge2 { type tn:enum_eplus; }
      leaf ge3 { type enum_eplus; }
      leaf ge4 {
        type enumeration {
          enum I_E_A { value 991; }
          enum I_E_B { value 992; }
          enum I_E_C { value 993; }
        }
      }
    }

    container show {
      container port {
        container counters {
          rwcli:cli-print-hook "test-cli-print-hook";
          leaf all {
            type empty;
          }
          leaf port-id {
            type uint32;
          }
        }
      }
    }
  }
}
