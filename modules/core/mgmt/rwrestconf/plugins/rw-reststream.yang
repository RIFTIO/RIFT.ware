/*
 * RIFT_IO_STANDARD_CMAKE_COPYRIGHT_HEADER(BEGIN)
 * Author(s): Max Beckett
 * Creation Date: 8/29/2015
 * RIFT_IO_STANDARD_CMAKE_COPYRIGHT_HEADER(END)
 */

module rw-reststream
{
  namespace "http://riftio.com/ns/riftware-1.0/rw-reststream";
  prefix "rw-reststream";

  import rw-base {
    prefix "rw-base";
  }

  import rw-manifest {
    prefix "rw-manifest";
  }

  import rw-vcs {
    prefix "rw-vcs";
  }

  description "RWRest Stream";
  revision 2015-08-29 {
    description "Initial version"; 
  }
}
