/*
 * STANDARD_RIFT_IO_COPYRIGHT
 *
 */

module rw-dyn-schema-test-b
{
  namespace "http://riftio.com/ns/riftware-1.0/rw-dyn-schema-test-b";
  prefix "rw-dyn-schema-test-b";

  description "Dynamic Schema Test Yang";
  revision 2015-10-15 {
    description "Initial version"; 
  }

  container dyn-schema-test-b {
    config true;
    leaf hello-world-b {
      type string;
    }
  }
}
