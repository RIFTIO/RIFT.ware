/*
 * STANDARD_RIFT_IO_COPYRIGHT
 *
 */

module rw-restportforward
{
  namespace "http://riftio.com/ns/riftware-1.0/rw-restportforward";
  prefix "rw-restportforward";

  import rw-pb-ext {
    prefix "rwpb";
  }

  import rw-mgmt-schema {
    prefix "rw-mgmt-schema";
  }

  description "RW RestPortforward configguration";
  revision 2015-10-12 {
    description "Initial version"; 
  }

  typedef rest-state {
    type enumeration {
      enum confd {
        description
        "Signifies that confd-rest is the primary rest server.";
      }
      enum rift {
        description
        "Signifies that rwrestconf is the primary rest server.";
      }
    }
  }

  container rwrestportforward-configuration {
    rwpb:msg-new "RestPortForwardConfig";    
    config true;

    leaf primary-rest-server {
      type rest-state;
    }
  }


}
